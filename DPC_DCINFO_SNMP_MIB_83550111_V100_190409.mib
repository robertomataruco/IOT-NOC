DPC-DISTRIBUTED-DCINFO-MIB DEFINITIONS ::= BEGIN

IMPORTS
    NOTIFICATION-TYPE, OBJECT-TYPE, MODULE-IDENTITY, 
    enterprises, Counter32, Integer32
        FROM SNMPv2-SMI
    NOTIFICATION-GROUP
        FROM SNMPv2-CONF
    DisplayString
        FROM SNMPv2-TC;

dpc MODULE-IDENTITY
    LAST-UPDATED "201904091850Z"
    ORGANIZATION 
        "Beijing Dynamic Power Shenzhen R&D(DPC)"
    CONTACT-INFO 
        "Beijing Dynamic Power Shenzhen R&D(DPC).
              Postal: 518000
              Shenzhen,China
              web:  www.dpc.com.cn"
    DESCRIPTION 
        "dpcDistributedPower is 10 of dpc.
         Branch overview:
         acDistribution is the branch of dpcDistributedPower`s node,which branch will be 1.
		 rectifier is the branch of dpcDistributedPower`s node,which branch will be 2.
		 dcDistribution is the branch of dpcDistributedPower`s node,which branch will be 3.
		 systemAlarm is the branch of dpcDistributedPower`s node,which branch will be 4. 
		 solarController is the branch of dpcDistributedPower`s node,which branch will be 5.
		 dcdcConverter is the branch of dpcDistributedPower`s node,which branch will be 6.
        "

    REVISION "201904091851Z"
    DESCRIPTION 
        "Version:V100
         First revision.
        
        
        Author Black"
        
        
             
::= { enterprises 39553 }
    
--
-- Node definitions
--
---------------------------------------------------------------
--  DPC Distribution Information{ DPC 10 }
--------------------------------------------------------------- 
    -- 1.3.6.1.4.1.39553.10
    dpcDistributedPower OBJECT IDENTIFIER ::= { dpc 10 }
    
------------------------------------------------------------
--  DC Distribution Information{ dpcDistributedPower 3 }
------------------------------------------------------------    
    -- 1.3.6.1.4.1.39553.10.3
    dcDistribution OBJECT IDENTIFIER ::= { dpcDistributedPower 3 }

------------------------------------------------------------
--  Analog signal for DC Distribution { dcDistribution 1 }
------------------------------------------------------------    
    -- 1.3.6.1.4.1.39553.10.3.1
    dcAnalog OBJECT IDENTIFIER ::= { dcDistribution 1 }

  -- 1.3.6.1.4.1.39553.10.3.1.1
    busVoltage OBJECT-TYPE
    SYNTAX INTEGER
    MAX-ACCESS read-only
    STATUS current
    DESCRIPTION 
        "The measured system bus voltage. 
         The actual value = The receive data / 100."
    ::= { dcAnalog 1 }
  -- 1.3.6.1.4.1.39553.10.3.1.2
    totalLoadCurrent OBJECT-TYPE
    SYNTAX INTEGER
    MAX-ACCESS read-only
    STATUS current
    DESCRIPTION 
        "The measured system total load current. 
         The actual value = The receive data / 100."
    ::= { dcAnalog 2 }
  -- 1.3.6.1.4.1.39553.10.3.1.3
    battery1Voltage OBJECT-TYPE
    SYNTAX INTEGER
    MAX-ACCESS read-only
    STATUS current
    DESCRIPTION 
        "The measured system battery group 1 voltage. 
         The actual value = The receive data / 100."
    ::= { dcAnalog 3 }
  -- 1.3.6.1.4.1.39553.10.3.1.4
    battery1Current OBJECT-TYPE
    SYNTAX INTEGER
    MAX-ACCESS read-only
    STATUS current
    DESCRIPTION 
        "The measured system battery group 1 current. 
         The actual value = The receive data / 100."
    ::= { dcAnalog 4 }
  -- 1.3.6.1.4.1.39553.10.3.1.5
    battery2Voltage OBJECT-TYPE
    SYNTAX INTEGER
    MAX-ACCESS read-only
    STATUS current
    DESCRIPTION 
        "The measured system battery group 2 voltage. 
         The actual value = The receive data / 100."
    ::= { dcAnalog 5 }
  -- 1.3.6.1.4.1.39553.10.3.1.6
    battery2Current OBJECT-TYPE
    SYNTAX INTEGER
    MAX-ACCESS read-only
    STATUS current
    DESCRIPTION 
        "The measured system battery group 2 current. 
         The actual value = The receive data / 100."
    ::= { dcAnalog 6 }
  -- 1.3.6.1.4.1.39553.10.3.1.7
    battery3Voltage OBJECT-TYPE
    SYNTAX INTEGER
    MAX-ACCESS read-only
    STATUS current
    DESCRIPTION 
        "The measured system battery group 3 voltage. 
         The actual value = The receive data / 100."
    ::= { dcAnalog 7 }
  -- 1.3.6.1.4.1.39553.10.3.1.8
    battery3Current OBJECT-TYPE
    SYNTAX INTEGER
    MAX-ACCESS read-only
    STATUS current
    DESCRIPTION 
        "The measured system battery group 3 current. 
         The actual value = The receive data / 100."
    ::= { dcAnalog 8 }
  -- 1.3.6.1.4.1.39553.10.3.1.9
    battery4Voltage OBJECT-TYPE
    SYNTAX INTEGER
    MAX-ACCESS read-only
    STATUS current
    DESCRIPTION 
        "The measured system battery group 4 voltage. 
         The actual value = The receive data / 100."
    ::= { dcAnalog 9 }
  -- 1.3.6.1.4.1.39553.10.3.1.10
    battery4Current OBJECT-TYPE
    SYNTAX INTEGER
    MAX-ACCESS read-only
    STATUS current
    DESCRIPTION 
        "The measured system battery group 4 current. 
         The actual value = The receive data / 100."
    ::= { dcAnalog 10 }
  -- 1.3.6.1.4.1.39553.10.3.1.11
    battery5Voltage OBJECT-TYPE
    SYNTAX INTEGER
    MAX-ACCESS read-only
    STATUS current
    DESCRIPTION 
        "The measured system battery group 5 voltage. 
         The actual value = The receive data / 100."
    ::= { dcAnalog 11 }
  -- 1.3.6.1.4.1.39553.10.3.1.12
    battery5Current OBJECT-TYPE
    SYNTAX INTEGER
    MAX-ACCESS read-only
    STATUS current
    DESCRIPTION 
        "The measured system battery group 5 current. 
         The actual value = The receive data / 100."
    ::= { dcAnalog 12 }
  -- 1.3.6.1.4.1.39553.10.3.1.13
    battery6Voltage OBJECT-TYPE
    SYNTAX INTEGER
    MAX-ACCESS read-only
    STATUS current
    DESCRIPTION 
        "The measured system battery group 6 voltage. 
         The actual value = The receive data / 100."
    ::= { dcAnalog 13 }
  -- 1.3.6.1.4.1.39553.10.3.1.14
    battery6Current OBJECT-TYPE
    SYNTAX INTEGER
    MAX-ACCESS read-only
    STATUS current
    DESCRIPTION 
        "The measured system battery group 6 current. 
         The actual value = The receive data / 100."
    ::= { dcAnalog 14 }
  -- 1.3.6.1.4.1.39553.10.3.1.15
    battery7Voltage OBJECT-TYPE
    SYNTAX INTEGER
    MAX-ACCESS read-only
    STATUS current
    DESCRIPTION 
        "The measured system battery group 7 voltage. 
         The actual value = The receive data / 100."
    ::= { dcAnalog 15 }
  -- 1.3.6.1.4.1.39553.10.3.1.16
    battery7Current OBJECT-TYPE
    SYNTAX INTEGER
    MAX-ACCESS read-only
    STATUS current
    DESCRIPTION 
        "The measured system battery group 7 current. 
         The actual value = The receive data / 100."
    ::= { dcAnalog 16 }
  -- 1.3.6.1.4.1.39553.10.3.1.17
    battery8Voltage OBJECT-TYPE
    SYNTAX INTEGER
    MAX-ACCESS read-only
    STATUS current
    DESCRIPTION 
        "The measured system battery group 8 voltage. 
         The actual value = The receive data / 100."
    ::= { dcAnalog 17 }
  -- 1.3.6.1.4.1.39553.10.3.1.18
    battery8Current OBJECT-TYPE
    SYNTAX INTEGER
    MAX-ACCESS read-only
    STATUS current
    DESCRIPTION 
        "The measured system battery group 8 current. 
         The actual value = The receive data / 100."
    ::= { dcAnalog 18 }
  -- 1.3.6.1.4.1.39553.10.3.1.19
    battery1MiddleVoltage OBJECT-TYPE
    SYNTAX INTEGER
    MAX-ACCESS read-only
    STATUS current
    DESCRIPTION 
        "The measured system battery group 1 middle point Voltage. 
         The actual value = The receive data / 100."
    ::= { dcAnalog 19 }
  -- 1.3.6.1.4.1.39553.10.3.1.20
    battery2MiddleVoltage OBJECT-TYPE
    SYNTAX INTEGER
    MAX-ACCESS read-only
    STATUS current
    DESCRIPTION 
        "The measured system battery group 2 middle point Voltage. 
         The actual value = The receive data / 100."
    ::= { dcAnalog 20 }
  -- 1.3.6.1.4.1.39553.10.3.1.21
    battery3MiddleVoltage OBJECT-TYPE
    SYNTAX INTEGER
    MAX-ACCESS read-only
    STATUS current
    DESCRIPTION 
        "The measured system battery group 3 middle point Voltage. 
         The actual value = The receive data / 100."
    ::= { dcAnalog 21 }
  -- 1.3.6.1.4.1.39553.10.3.1.22
    battery4MiddleVoltage OBJECT-TYPE
    SYNTAX INTEGER
    MAX-ACCESS read-only
    STATUS current
    DESCRIPTION 
        "The measured system battery group 4 middle point Voltage. 
         The actual value = The receive data / 100."
    ::= { dcAnalog 22 }
  -- 1.3.6.1.4.1.39553.10.3.1.23
    battery5MiddleVoltage OBJECT-TYPE
    SYNTAX INTEGER
    MAX-ACCESS read-only
    STATUS current
    DESCRIPTION 
        "The measured system battery group 5 middle point Voltage. 
         The actual value = The receive data / 100."
    ::= { dcAnalog 23 }
  -- 1.3.6.1.4.1.39553.10.3.1.24
    battery6MiddleVoltage OBJECT-TYPE
    SYNTAX INTEGER
    MAX-ACCESS read-only
    STATUS current
    DESCRIPTION 
        "The measured system battery group 6 middle point Voltage. 
         The actual value = The receive data / 100."
    ::= { dcAnalog 24 }
  -- 1.3.6.1.4.1.39553.10.3.1.25
    battery7MiddleVoltage OBJECT-TYPE
    SYNTAX INTEGER
    MAX-ACCESS read-only
    STATUS current
    DESCRIPTION 
        "The measured system battery group 7 middle point Voltage. 
         The actual value = The receive data / 100."
    ::= { dcAnalog 25 }
  -- 1.3.6.1.4.1.39553.10.3.1.26
    battery8MiddleVoltage OBJECT-TYPE
    SYNTAX INTEGER
    MAX-ACCESS read-only
    STATUS current
    DESCRIPTION 
        "The measured system battery group 8 middle point Voltage. 
         The actual value = The receive data / 100."
    ::= { dcAnalog 26 }
  -- 1.3.6.1.4.1.39553.10.3.1.27  
    batteryStatus OBJECT-TYPE
    SYNTAX INTEGER {
        discharge (0),
        boost (1),
        float (2),
        test (3),
        constantcurrentboost (4)
    }
    MAX-ACCESS read-only
    STATUS current
    DESCRIPTION 
        "The system current status for the battery."
    ::= { dcAnalog 27 }
    -- 1.3.6.1.4.1.39553.10.3.1.799
    temperature1 OBJECT-TYPE
    SYNTAX INTEGER
    MAX-ACCESS read-only
    STATUS current
    DESCRIPTION     
        "The measured temperature of sensor 1(controller inner sensor). 
         The actual value = The receive data / 100.
         The unit of actual value is degree centigrade.
         If  receive value is greater than 10000 or less than -5000,temperature is invalid"
    ::= { dcAnalog 799 }
  -- 1.3.6.1.4.1.39553.10.3.1.800
    temperature2 OBJECT-TYPE
    SYNTAX INTEGER
    MAX-ACCESS read-only
    STATUS current
    DESCRIPTION     
        "The measured temperature of sensor 2(controller inner sensor). 
         The actual value = The receive data / 100.
         The unit of actual value is degree centigrade.
         If  receive value is greater than 10000 or less than -5000,temperature is invalid"
    ::= { dcAnalog 800 }
  -- 1.3.6.1.4.1.39553.10.3.1.801
    ex1Temperature1 OBJECT-TYPE
    SYNTAX INTEGER
    MAX-ACCESS read-only
    STATUS current
    DESCRIPTION     
        "The measured temperature of sensor 1 of SC320-1. 
         The actual value = The receive data / 100.
         The unit of actual value is degree centigrade.
         If  receive value is greater than 10000 or less than -5000,temperature is invalid"
    ::= { dcAnalog 801 }
  -- 1.3.6.1.4.1.39553.10.3.1.802
    ex1Temperature2 OBJECT-TYPE
    SYNTAX INTEGER
    MAX-ACCESS read-only
    STATUS current
    DESCRIPTION     
        "The measured temperature of sensor 2 of SC320-1. 
         The actual value = The receive data / 100.
         The unit of actual value is degree centigrade.
         If  receive value is greater than 10000 or less than -5000,temperature is invalid"
    ::= { dcAnalog 802 }
  -- 1.3.6.1.4.1.39553.10.3.1.803
    ex1EnvironmentTemperature OBJECT-TYPE
    SYNTAX INTEGER
    MAX-ACCESS read-only
    STATUS current
    DESCRIPTION     
        "The measured temperature of environment of SC320-1. 
         The actual value = The receive data / 100.
         The unit of actual value is degree centigrade.
         If  receive value is greater than 10000 or less than -5000,temperature is invalid"
    ::= { dcAnalog 803 }
  -- 1.3.6.1.4.1.39553.10.3.1.804
    ex1Humidity OBJECT-TYPE
    SYNTAX INTEGER
    MAX-ACCESS read-only
    STATUS current
    DESCRIPTION     
        "The measured humidity of SC320-1. 
         The actual value = The receive data / 100.
         The unit of actual value is %."
    ::= { dcAnalog 804 }
  -- 1.3.6.1.4.1.39553.10.3.1.805
    battery1CapacityLeft OBJECT-TYPE
    SYNTAX INTEGER
    MAX-ACCESS read-only
    STATUS current
    DESCRIPTION     
        "Capacity left in the battery group 1. 
         The actual value = The receive data / 100.
         The unit of actual value is %."
    ::= { dcAnalog 805 }
  -- 1.3.6.1.4.1.39553.10.3.1.806
    battery2CapacityLeft OBJECT-TYPE
    SYNTAX INTEGER
    MAX-ACCESS read-only
    STATUS current
    DESCRIPTION     
        "Capacity left in the battery group 2. 
         The actual value = The receive data / 100.
         The unit of actual value is %."
    ::= { dcAnalog 806 }
  -- 1.3.6.1.4.1.39553.10.3.1.807
    battery3CapacityLeft OBJECT-TYPE
    SYNTAX INTEGER
    MAX-ACCESS read-only
    STATUS current
    DESCRIPTION     
        "Capacity left in the battery group 3. 
         The actual value = The receive data / 100.
         The unit of actual value is %."
    ::= { dcAnalog 807 }
  -- 1.3.6.1.4.1.39553.10.3.1.808
    battery4CapacityLeft OBJECT-TYPE
    SYNTAX INTEGER
    MAX-ACCESS read-only
    STATUS current
    DESCRIPTION     
        "Capacity left in the battery group 4. 
         The actual value = The receive data / 100.
         The unit of actual value is %."
    ::= { dcAnalog 808 }
  -- 1.3.6.1.4.1.39553.10.3.1.809
    battery5CapacityLeft OBJECT-TYPE
    SYNTAX INTEGER
    MAX-ACCESS read-only
    STATUS current
    DESCRIPTION     
        "Capacity left in the battery group 5. 
         The actual value = The receive data / 100.
         The unit of actual value is %."
    ::= { dcAnalog 809 }
  -- 1.3.6.1.4.1.39553.10.3.1.810
    battery6CapacityLeft OBJECT-TYPE
    SYNTAX INTEGER
    MAX-ACCESS read-only
    STATUS current
    DESCRIPTION     
        "Capacity left in the battery group 6. 
         The actual value = The receive data / 100.
         The unit of actual value is %."
    ::= { dcAnalog 810 }
  -- 1.3.6.1.4.1.39553.10.3.1.811
    battery7CapacityLeft OBJECT-TYPE
    SYNTAX INTEGER
    MAX-ACCESS read-only
    STATUS current
    DESCRIPTION     
        "Capacity left in the battery group 7. 
         The actual value = The receive data / 100.
         The unit of actual value is %."
    ::= { dcAnalog 811 }
  -- 1.3.6.1.4.1.39553.10.3.1.812
    battery8CapacityLeft OBJECT-TYPE
    SYNTAX INTEGER
    MAX-ACCESS read-only
    STATUS current
    DESCRIPTION     
        "Capacity left in the battery group 8. 
         The actual value = The receive data / 100.
         The unit of actual value is %."
    ::= { dcAnalog 812 }
    -- 1.3.6.1.4.1.39553.10.3.1.814
    dcPower OBJECT-TYPE
    SYNTAX INTEGER
    MAX-ACCESS read-only
    STATUS current
    DESCRIPTION     
        "The total output DC power of system. 
         The actual value = The receive data / 1000.
         The unit of actual value is KW."
    ::= { dcAnalog 814 }
    -- 1.3.6.1.4.1.39553.10.3.1.815
    dcEnergy OBJECT-TYPE
    SYNTAX INTEGER
    MAX-ACCESS read-only
    STATUS current
    DESCRIPTION     
        "The total output DC Energy of system. 
         The actual value = The receive data / 100.
         The unit of actual value is KWH."
    ::= { dcAnalog 815 }
    -- 1.3.6.1.4.1.39553.10.3.1.816
    ex2Temperature1 OBJECT-TYPE
    SYNTAX INTEGER
    MAX-ACCESS read-only
    STATUS current
    DESCRIPTION     
        "The measured temperature of sensor 1 of SC320-2. 
         The actual value = The receive data / 100.                                                         
         The unit of actual value is degree centigrade.
         If  receive value is greater than 10000 or less than -5000,temperature is invalid"
    ::= { dcAnalog 816 }
    -- 1.3.6.1.4.1.39553.10.3.1.817
    ex2Temperature2 OBJECT-TYPE
    SYNTAX INTEGER
    MAX-ACCESS read-only
    STATUS current
    DESCRIPTION     
        "The measured temperature of sensor 2 of SC320-2. 
         The actual value = The receive data / 100.
         The unit of actual value is degree centigrade.
         If  receive value is greater than 10000 or less than -5000,temperature is invalid"
    ::= { dcAnalog 817 }
    -- 1.3.6.1.4.1.39553.10.3.1.818
    ex2EnvironmentTemperature OBJECT-TYPE
    SYNTAX INTEGER
    MAX-ACCESS read-only
    STATUS current
    DESCRIPTION     
        "The measured temperature of environment of SC320-2. 
         The actual value = The receive data / 100.
         The unit of actual value is degree centigrade.
         If  receive value is greater than 10000 or less than -5000,temperature is invalid"
    ::= { dcAnalog 818 }
    -- 1.3.6.1.4.1.39553.10.3.1.819
    ex2Humidity OBJECT-TYPE
    SYNTAX INTEGER
    MAX-ACCESS read-only
    STATUS current
    DESCRIPTION     
        "The measured humidity of SC320-2. 
         The actual value = The receive data / 100.
         The unit of actual value is %."
    ::= { dcAnalog 819 }
    -- 1.3.6.1.4.1.39553.10.3.1.820
    ex3Temperature1 OBJECT-TYPE
    SYNTAX INTEGER
    MAX-ACCESS read-only
    STATUS current
    DESCRIPTION     
        "The measured temperature of sensor 1 of SC320-3. 
         The actual value = The receive data / 100.
         The unit of actual value is degree centigrade.
         If  receive value is greater than 10000 or less than -5000,temperature is invalid"
    ::= { dcAnalog 820 }
    -- 1.3.6.1.4.1.39553.10.3.1.821
    ex3Temperature2 OBJECT-TYPE
    SYNTAX INTEGER
    MAX-ACCESS read-only
    STATUS current
    DESCRIPTION     
        "The measured temperature of sensor 2 of SC320-3. 
         The actual value = The receive data / 100.
         The unit of actual value is degree centigrade.
         If  receive value is greater than 10000 or less than -5000,temperature is invalid"
    ::= { dcAnalog 821 }
    -- 1.3.6.1.4.1.39553.10.3.1.822
    ex3EnvironmentTemperature OBJECT-TYPE
    SYNTAX INTEGER
    MAX-ACCESS read-only
    STATUS current
    DESCRIPTION     
        "The measured temperature of environment of SC320-3. 
         The actual value = The receive data / 100.
         The unit of actual value is degree centigrade.
         If  receive value is greater than 10000 or less than -5000,temperature is invalid"
    ::= { dcAnalog 822 }
    -- 1.3.6.1.4.1.39553.10.3.1.823
    ex3Humidity OBJECT-TYPE
    SYNTAX INTEGER
    MAX-ACCESS read-only
    STATUS current
    DESCRIPTION     
        "The measured humidity of SC320-3. 
         The actual value = The receive data / 100.
         The unit of actual value is %."
    ::= { dcAnalog 823 }
    -- 1.3.6.1.4.1.39553.10.3.1.824
    ex4Temperature1 OBJECT-TYPE
    SYNTAX INTEGER
    MAX-ACCESS read-only
    STATUS current
    DESCRIPTION     
        "The measured temperature of sensor 1 of SC320-4. 
         The actual value = The receive data / 100.
         The unit of actual value is degree centigrade.
         If  receive value is greater than 10000 or less than -5000,temperature is invalid"
    ::= { dcAnalog 824 }
    -- 1.3.6.1.4.1.39553.10.3.1.822
    ex4Temperature2 OBJECT-TYPE
    SYNTAX INTEGER
    MAX-ACCESS read-only
    STATUS current
    DESCRIPTION     
        "The measured temperature of sensor 2 of SC320-4. 
         The actual value = The receive data / 100.
         The unit of actual value is degree centigrade.
         If  receive value is greater than 10000 or less than -5000,temperature is invalid"
    ::= { dcAnalog 825 }
    -- 1.3.6.1.4.1.39553.10.3.1.826
    ex4EnvironmentTemperature OBJECT-TYPE
    SYNTAX INTEGER
    MAX-ACCESS read-only
    STATUS current
    DESCRIPTION     
        "The measured temperature of environment of SC320-4. 
         The actual value = The receive data / 100.
         The unit of actual value is degree centigrade.
         If  receive value is greater than 10000 or less than -5000,temperature is invalid"
    ::= { dcAnalog 826 }
    -- 1.3.6.1.4.1.39553.10.3.1.827
    ex4Humidity OBJECT-TYPE
    SYNTAX INTEGER
    MAX-ACCESS read-only
    STATUS current
    DESCRIPTION     
        "The measured humidity of SC320-4. 
         The actual value = The receive data / 100.
         The unit of actual value is %."
    ::= { dcAnalog 827 }
    -- 1.3.6.1.4.1.39553.10.3.1.828
    ex5Temperature1 OBJECT-TYPE
    SYNTAX INTEGER
    MAX-ACCESS read-only
    STATUS current
    DESCRIPTION     
        "The measured temperature of sensor 1 of SC320-5. 
         The actual value = The receive data / 100.
         The unit of actual value is degree centigrade.
         If  receive value is greater than 10000 or less than -5000,temperature is invalid"
    ::= { dcAnalog 828 }
    -- 1.3.6.1.4.1.39553.10.3.1.829
    ex5Temperature2 OBJECT-TYPE
    SYNTAX INTEGER
    MAX-ACCESS read-only
    STATUS current
    DESCRIPTION     
        "The measured temperature of sensor 2 of SC320-5. 
         The actual value = The receive data / 100.
         The unit of actual value is degree centigrade.
         If  receive value is greater than 10000 or less than -5000,temperature is invalid"
    ::= { dcAnalog 829 }
    -- 1.3.6.1.4.1.39553.10.3.1.830
    ex5EnvironmentTemperature OBJECT-TYPE
    SYNTAX INTEGER
    MAX-ACCESS read-only
    STATUS current
    DESCRIPTION     
        "The measured temperature of environment of SC320-5. 
         The actual value = The receive data / 100.
         The unit of actual value is degree centigrade.
         If  receive value is greater than 10000 or less than -5000,temperature is invalid"
    ::= { dcAnalog 830 }
    -- 1.3.6.1.4.1.39553.10.3.1.831
    ex5Humidity OBJECT-TYPE
    SYNTAX INTEGER
    MAX-ACCESS read-only
    STATUS current
    DESCRIPTION     
        "The measured humidity of SC320-5. 
         The actual value = The receive data / 100.
         The unit of actual value is %."
    ::= { dcAnalog 831 }
    

------------------------------------------------------------
-- DC branch information table { dcAnalog 1072 }
------------------------------------------------------------

dcBranchInfoTable OBJECT-TYPE
    SYNTAX SEQUENCE OF DCBranchInfoEntry
    MAX-ACCESS not-accessible
    STATUS current
    DESCRIPTION "
        Table holding information about the currently DC branch."
    ::= { dcAnalog 1072 }

dcBranchInfoEntry OBJECT-TYPE
    SYNTAX DCBranchInfoEntry
    MAX-ACCESS not-accessible
    STATUS current
    DESCRIPTION "
        An entry (conceptual row) in the dcBranchInfoTable."
    INDEX { dcBranchIndex }
    ::= { dcBranchInfoTable 1 }

DCBranchInfoEntry ::= SEQUENCE {
        dcBranchIndex INTEGER,
        dcBranchcurrent INTEGER,
        slightOverCurrent INTEGER,
        severeOverCurrent INTEGER
    }

    dcBranchIndex OBJECT-TYPE
    SYNTAX INTEGER {
        dcBranch1   (1),
        dcBranch2   (2),
        dcBranch3   (3),
        dcBranch4   (4),
        dcBranch5   (5),
        dcBranch6   (6),
        dcBranch7   (7),
        dcBranch8   (8),
        dcBranch9   (9),
        dcBranch10  (10),
        dcBranch11  (11),
        dcBranch12  (12),
        dcBranch13  (13),
        dcBranch14  (14),
        dcBranch15  (15),
        dcBranch16  (16),
        dcBranch17  (17),
        dcBranch18  (18),
        dcBranch19  (19),
        dcBranch20  (20),
        dcBranch21  (21),
        dcBranch22  (22),
        dcBranch23  (23),
        dcBranch24  (24),
        dcBranch25  (25),
        dcBranch26  (26),
        dcBranch27  (27),
        dcBranch28  (28),
        dcBranch29  (29),
        dcBranch30  (30),
        dcBranch31  (31),
        dcBranch32  (32),
        dcBranch33  (33),
        dcBranch34  (34),
        dcBranch35  (35),
        dcBranch36  (36),
        dcBranch37  (37),
        dcBranch38  (38),
        dcBranch39  (39),
        dcBranch40  (40),
        dcBranch41  (41),
        dcBranch42  (42),
        dcBranch43  (43),
        dcBranch44  (44),
        dcBranch45  (45),
        dcBranch46  (46),
        dcBranch47  (47),
        dcBranch48  (48),
        dcBranch49  (49),
        dcBranch50  (50),
        dcBranch51  (51),
        dcBranch52  (52),
        dcBranch53  (53),
        dcBranch54  (54),
        dcBranch55  (55),
        dcBranch56  (56),
        dcBranch57  (57),
        dcBranch58  (58),
        dcBranch59  (59),
        dcBranch60  (60),
        dcBranch61  (61),
        dcBranch62  (62),
        dcBranch63  (63),
        dcBranch64  (64),
        dcBranch65  (65),
        dcBranch66  (66),
        dcBranch67  (67),
        dcBranch68  (68),
        dcBranch69  (69),
        dcBranch70  (70),
        dcBranch71  (71),
        dcBranch72  (72)
    }
    MAX-ACCESS read-only
    STATUS current
    DESCRIPTION "
        The unique sequence number of DC branch.
        dcBranch1   (1),
        dcBranch2   (2),
        dcBranch3   (3),
        dcBranch4   (4),
        dcBranch5   (5),
        dcBranch6   (6),
        dcBranch7   (7),
        dcBranch8   (8),
        dcBranch9   (9),
        dcBranch10  (10),
        dcBranch11  (11),
        dcBranch12  (12),
        dcBranch13  (13),
        dcBranch14  (14),
        dcBranch15  (15),
        dcBranch16  (16),
        dcBranch17  (17),
        dcBranch18  (18),
        dcBranch19  (19),
        dcBranch20  (20),
        dcBranch21  (21),
        dcBranch22  (22),
        dcBranch23  (23),
        dcBranch24  (24),
        dcBranch25  (25),
        dcBranch26  (26),
        dcBranch27  (27),
        dcBranch28  (28),
        dcBranch29  (29),
        dcBranch30  (30),
        dcBranch31  (31),
        dcBranch32  (32),
        dcBranch33  (33),
        dcBranch34  (34),
        dcBranch35  (35),
        dcBranch36  (36),
        dcBranch37  (37),
        dcBranch38  (38),
        dcBranch39  (39),
        dcBranch40  (40),
        dcBranch41  (41),
        dcBranch42  (42),
        dcBranch43  (43),
        dcBranch44  (44),
        dcBranch45  (45),
        dcBranch46  (46),
        dcBranch47  (47),
        dcBranch48  (48),
        dcBranch49  (49),
        dcBranch50  (50),
        dcBranch51  (51),
        dcBranch52  (52),
        dcBranch53  (53),
        dcBranch54  (54),
        dcBranch55  (55),
        dcBranch56  (56),
        dcBranch57  (57),
        dcBranch58  (58),
        dcBranch59  (59),
        dcBranch60  (60),
        dcBranch61  (61),
        dcBranch62  (62),
        dcBranch63  (63),
        dcBranch64  (64),
        dcBranch65  (65),
        dcBranch66  (66),
        dcBranch67  (67),
        dcBranch68  (68),
        dcBranch69  (69),
        dcBranch70  (70),
        dcBranch71  (71),
        dcBranch72  (72),
        "
    ::= { dcBranchInfoEntry 1 }

    dcBranchcurrent OBJECT-TYPE
    SYNTAX INTEGER
    MAX-ACCESS read-only
    STATUS current
    DESCRIPTION "
        DC branch current.
         The actual value = The receive data/100.
         The unit of actual value is ampere"
    ::= { dcBranchInfoEntry 2 }
    
    slightOverCurrent OBJECT-TYPE
    SYNTAX INTEGER {
        normal (0),
        alarm (1)
    }
    MAX-ACCESS read-only
    STATUS current
    DESCRIPTION "
        DC branch slight over current alarm state.
         normal (0),
        alarm (1)"
    ::= { dcBranchInfoEntry 3 }
    
    severeOverCurrent OBJECT-TYPE
    SYNTAX INTEGER {
        normal (0),
        alarm (1)
    }
    MAX-ACCESS read-only
    STATUS current
    DESCRIPTION "
        DC branch severe over current alarm state.
         normal (0),
        alarm (1)"
    ::= { dcBranchInfoEntry 4 }


------------------------------------------------------------
-- Battery information table { dcAnalog 1073 }
------------------------------------------------------------

batteryInfoTable OBJECT-TYPE
    SYNTAX SEQUENCE OF BatteryInfoEntry
    MAX-ACCESS not-accessible
    STATUS current
    DESCRIPTION "
        Table holding information about the currently battery."
    ::= { dcAnalog 1073 }

batteryInfoEntry OBJECT-TYPE
    SYNTAX BatteryInfoEntry
    MAX-ACCESS not-accessible
    STATUS current
    DESCRIPTION "
        An entry (conceptual row) in the batteryInfoTable."
    INDEX { batteryIndex }
    ::= { batteryInfoTable 1 }

BatteryInfoEntry ::= SEQUENCE {
        batteryIndex INTEGER,
        batteryCurrent INTEGER,
        batteryVoltage INTEGER,
        batterySOC INTEGER,
        middleVoltage INTEGER,
        totalCapacity INTEGER,
        batteryTemperature INTEGER,
        cannotCharge INTEGER
    }

    batteryIndex OBJECT-TYPE
    SYNTAX INTEGER {
        battery1    (1),
        battery2    (2),
        battery3    (3),
        battery4    (4),
        battery5    (5),
        battery6    (6),
        battery7    (7),
        battery8    (8)
    }
    MAX-ACCESS read-only
    STATUS current
    DESCRIPTION "
        The unique sequence number of battery.
        battery1    (1),
        battery2    (2),
        battery3    (3),
        battery4    (4),
        battery5    (5),
        battery6    (6),
        battery7    (7),
        battery8    (8),
        "
    ::= { batteryInfoEntry 1 }

    batteryCurrent OBJECT-TYPE
    SYNTAX INTEGER
    MAX-ACCESS read-only
    STATUS current
    DESCRIPTION "
        Battery current.
         The actual value = The receive data/100.
         The unit of actual value is ampere"
    ::= { batteryInfoEntry 2 }
    
    batteryVoltage OBJECT-TYPE
    SYNTAX INTEGER
    MAX-ACCESS read-only
    STATUS current
    DESCRIPTION "
        Battery voltage.
         The actual value = The receive data/100.
         The unit of actual value is volt"
    ::= { batteryInfoEntry 3 }
    
    batterySOC OBJECT-TYPE
    SYNTAX INTEGER
    MAX-ACCESS read-only
    STATUS current
    DESCRIPTION "
        Battery SOC.
         The actual value = The receive data/100.
         The unit of actual value is percent"
    ::= { batteryInfoEntry 4 }
    
    middleVoltage OBJECT-TYPE
    SYNTAX INTEGER
    MAX-ACCESS read-only
    STATUS current
    DESCRIPTION "
        Battery middle voltage.
         The actual value = The receive data/100.
         The unit of actual value is volt"
    ::= { batteryInfoEntry 5 }
    
    totalCapacity OBJECT-TYPE
    SYNTAX INTEGER
    MAX-ACCESS read-write
    STATUS current
    DESCRIPTION "
        Battery total capacity.
         The actual value = The receive data/100.
         The unit of actual value is AH"
    ::= { batteryInfoEntry 6 }
    
    batteryTemperature OBJECT-TYPE
    SYNTAX INTEGER
    MAX-ACCESS read-only
    STATUS current
    DESCRIPTION "
        Battery temperature.
         The actual value = The receive data/100.
         The unit of actual value is degree centigrade.
         If  receive value is greater than 10000 or less than -5000,temperature is invalid"
    ::= { batteryInfoEntry 7 }
    
    cannotCharge OBJECT-TYPE
    SYNTAX INTEGER {
        normal (0),
        alarm (1)
    }
    MAX-ACCESS read-only
    STATUS current
    DESCRIPTION "
        Battery can not charge alarm state.
         normal (0),
        alarm (1)"
    ::= { batteryInfoEntry 8 }

------------------------------------------------------------
-- EX temperature information table { dcAnalog 1074 }
------------------------------------------------------------

exTemperatureTable OBJECT-TYPE
    SYNTAX SEQUENCE OF ExTemperatureEntry
    MAX-ACCESS not-accessible
    STATUS current
    DESCRIPTION "
        Table holding information of temperature about the SC320."
    ::= { dcAnalog 1074 }

exTemperatureEntry OBJECT-TYPE
    SYNTAX ExTemperatureEntry
    MAX-ACCESS not-accessible
    STATUS current
    DESCRIPTION "
        An entry (conceptual row) in the exTemperatureTable."
    INDEX { batteryIndex }
    ::= { exTemperatureTable 1 }

ExTemperatureEntry ::= SEQUENCE {
        sc320Index INTEGER,
        temperature_1 INTEGER,
        temperature_2 INTEGER,
        temperature_3 INTEGER,
        humidity INTEGER
    }

    sc320Index OBJECT-TYPE
    SYNTAX INTEGER {
        sc320-1 (1),
        sc320-2 (2),
        sc320-3 (3),
        sc320-4 (4),
        sc320-5 (5)
    }
    MAX-ACCESS read-only
    STATUS current
    DESCRIPTION "
        The unique sequence number of SC320.
        sc320-1 (1),
        sc320-2 (2),
        sc320-3 (3),
        sc320-4 (4),
        sc320-5 (5)
        "
    ::= { exTemperatureEntry 1 }

    temperature_1 OBJECT-TYPE
    SYNTAX INTEGER
    MAX-ACCESS read-only
    STATUS current
    DESCRIPTION "
        Temperature 1.
         The actual value = The receive data/100.
         The unit of actual value is degree centigrade.
         If  receive value is greater than 10000 or less than -5000,temperature is invalid"
    ::= { exTemperatureEntry 2 }
    
    temperature_2 OBJECT-TYPE
    SYNTAX INTEGER
    MAX-ACCESS read-only
    STATUS current
    DESCRIPTION "
        Temperature 2.
         The actual value = The receive data/100.
         The unit of actual value is degree centigrade.
         If  receive value is greater than 10000 or less than -5000,temperature is invalid"
    ::= { exTemperatureEntry 3 }
    
    temperature_3 OBJECT-TYPE
    SYNTAX INTEGER
    MAX-ACCESS read-only
    STATUS current
    DESCRIPTION "
        Temperature 3.
         The actual value = The receive data/100.
         The unit of actual value is degree centigrade.
         If  receive value is greater than 10000 or less than -5000,temperature is invalid"
    ::= { exTemperatureEntry 4 }
    
    humidity OBJECT-TYPE
    SYNTAX INTEGER
    MAX-ACCESS read-only
    STATUS current
    DESCRIPTION "
        Humidity.
         The actual value = The receive data/100.
         The unit of actual value is %.
         If  receive value is greater than 10000 or less than 0,temperature is invalid"
    ::= { exTemperatureEntry 5 }
    
------------------------------------------------------------
-- Current Alarm Status { dcDistribution 2 }
------------------------------------------------------------    
-- 1.3.6.1.4.1.39553.10.3.2
    dcAlarmStatus OBJECT IDENTIFIER ::= { dcDistribution 2 }

  -- 1.3.6.1.4.1.39553.10.3.2.1
    dcBranchFuseAlarm1To32 OBJECT-TYPE
    SYNTAX INTEGER
    MAX-ACCESS read-only
    STATUS current
    DESCRIPTION     
        "The DC load branch fuse 1 to 32 break alarm.
         The bit0 to bit31 for the receive data means the DC load fuse 1 to 32 status.
         The value 1 means alarm happen for the each bit. 
         And the value of 0 means no alarm for each bit."
    ::= { dcAlarmStatus 1 }
  -- 1.3.6.1.4.1.39553.10.3.2.2
    dcBranchFuseAlarm33To64 OBJECT-TYPE
    SYNTAX INTEGER
    MAX-ACCESS read-only
    STATUS current
    DESCRIPTION     
        "The DC load branch fuse 33 to 64 break alarm.
         The bit0 to bit31 for the receive data means the DC load fuse 33 to 64 status.
         The value 1 means alarm happen for the each bit. 
         And the value of 0 means no alarm for each bit."
    ::= { dcAlarmStatus 2 }
  -- 1.3.6.1.4.1.39553.10.3.2.3
    dcBranchFuseAlarm65To96 OBJECT-TYPE
    SYNTAX INTEGER
    MAX-ACCESS read-only
    STATUS current
    DESCRIPTION     
        "The DC load branch fuse 65 to 96 break alarm.
         The bit0 to bit31 for the receive data means the DC load fuse 65 to 96 status.
         The value 1 means alarm happen for the each bit. 
         And the value of 0 means no alarm for each bit."
    ::= { dcAlarmStatus 3 }
  -- 1.3.6.1.4.1.39553.10.3.2.4
    dcBranchFuseAlarm97To128 OBJECT-TYPE
    SYNTAX INTEGER
    MAX-ACCESS read-only
    STATUS current
    DESCRIPTION     
        "The DC load branch fuse 97 to 128 break alarm.
         The bit0 to bit31 for the receive data means the DC load fuse 97 to 128 status.
         The value 1 means alarm happen for the each bit. 
         And the value of 0 means no alarm for each bit."
    ::= { dcAlarmStatus 4 }
  -- 1.3.6.1.4.1.39553.10.3.2.5
    dcBranchFuseAlarm129To160 OBJECT-TYPE
    SYNTAX INTEGER
    MAX-ACCESS read-only
    STATUS current
    DESCRIPTION     
        "The DC load branch fuse 129 to 160 break alarm.
         The bit0 to bit31 for the receive data means the DC load fuse 129 to 160 status.
         The value 1 means alarm happen for the each bit. 
         And the value of 0 means no alarm for each bit."
    ::= { dcAlarmStatus 5 }
  -- 1.3.6.1.4.1.39553.10.3.2.6
    dcBranchFuseAlarm161To192 OBJECT-TYPE
    SYNTAX INTEGER
    MAX-ACCESS read-only
    STATUS current
    DESCRIPTION     
        "The DC load branch fuse 161 to 192 break alarm.
         The bit0 to bit31 for the receive data means the DC load fuse 161 to 192 status.
         The value 1 means alarm happen for the each bit. 
         And the value of 0 means no alarm for each bit."
    ::= { dcAlarmStatus 6 }
  -- 1.3.6.1.4.1.39553.10.3.2.7
    dcBranchFuseAlarm193To224 OBJECT-TYPE
    SYNTAX INTEGER
    MAX-ACCESS read-only
    STATUS current
    DESCRIPTION     
        "The DC load branch fuse 193 to 224 break alarm.
         The bit0 to bit31 for the receive data means the DC load fuse 193 to 224 status.
         The value 1 means alarm happen for the each bit. 
         And the value of 0 means no alarm for each bit."
    ::= { dcAlarmStatus 7 }
  -- 1.3.6.1.4.1.39553.10.3.2.8
    dcBranchFuseAlarm225To256 OBJECT-TYPE
    SYNTAX INTEGER
    MAX-ACCESS read-only
    STATUS current
    DESCRIPTION     
        "The DC load branch fuse 225 to 256 break alarm.
         The bit0 to bit31 for the receive data means the DC load fuse 225 to 256 status.
         The value 1 means alarm happen for the each bit. 
         And the value of 0 means no alarm for each bit."
    ::= { dcAlarmStatus 8 }
  -- 1.3.6.1.4.1.39553.10.3.2.17
    dcBranchSevereOverCurrentAlarm1To32 OBJECT-TYPE
    SYNTAX INTEGER
    MAX-ACCESS read-only
    STATUS current
    DESCRIPTION     
        "The DC load branch 1 to 32 severe over current alarm.
         The bit0 to bit31 for the receive data means the 
         DC load branch 1 to 32 severe over current alarm status.
         The value 1 means alarm happen for the each bit. 
         And the value of 0 means no alarm for each bit."
    ::= { dcAlarmStatus 17 }
  -- 1.3.6.1.4.1.39553.10.3.2.18
    dcBranchSevereOverCurrentAlarm33To64 OBJECT-TYPE
    SYNTAX INTEGER
    MAX-ACCESS read-only
    STATUS current
    DESCRIPTION     
        "The DC load branch 33 to 64 severe over current alarm.
         The bit0 to bit31 for the receive data means the 
         DC load branch 33 to 64 severe over current alarm status.
         The value 1 means alarm happen for the each bit. 
         And the value of 0 means no alarm for each bit."
    ::= { dcAlarmStatus 18 }
  -- 1.3.6.1.4.1.39553.10.3.2.19
    dcBranchSevereOverCurrentAlarm65To96 OBJECT-TYPE
    SYNTAX INTEGER
    MAX-ACCESS read-only
    STATUS current
    DESCRIPTION     
        "The DC load branch 65 to 96 severe over current alarm.
         The bit0 to bit31 for the receive data means the 
         DC load branch 65 to 96 severe over current alarm status.
         The value 1 means alarm happen for the each bit. 
         And the value of 0 means no alarm for each bit."
    ::= { dcAlarmStatus 19 }
  -- 1.3.6.1.4.1.39553.10.3.2.20
    dcBranchSevereOverCurrentAlarm97To128 OBJECT-TYPE
    SYNTAX INTEGER
    MAX-ACCESS read-only
    STATUS current
    DESCRIPTION     
        "The DC load branch 97 to 128 severe over current alarm.
         The bit0 to bit31 for the receive data means the 
         DC load branch 97 to 128 severe over current alarm status.
         The value 1 means alarm happen for the each bit. 
         And the value of 0 means no alarm for each bit."
    ::= { dcAlarmStatus 20 }
  -- 1.3.6.1.4.1.39553.10.3.2.21
    dcBranchSevereOverCurrentAlarm129To160 OBJECT-TYPE
    SYNTAX INTEGER
    MAX-ACCESS read-only
    STATUS current
    DESCRIPTION     
        "The DC load branch 129 to 160 severe over current alarm.
         The bit0 to bit31 for the receive data means the 
         DC load branch 129 to 160 severe over current alarm status.
         The value 1 means alarm happen for the each bit. 
         And the value of 0 means no alarm for each bit."
    ::= { dcAlarmStatus 21 }
  -- 1.3.6.1.4.1.39553.10.3.2.22
    dcBranchSevereOverCurrentAlarm161To192 OBJECT-TYPE
    SYNTAX INTEGER
    MAX-ACCESS read-only
    STATUS current
    DESCRIPTION     
        "The DC load branch 161 to 192 severe over current alarm.
         The bit0 to bit31 for the receive data means the 
         DC load branch 161 to 192 severe over current alarm status.
         The value 1 means alarm happen for the each bit. 
         And the value of 0 means no alarm for each bit."
    ::= { dcAlarmStatus 22 }
  -- 1.3.6.1.4.1.39553.10.3.2.23
    dcBranchSevereOverCurrentAlarm193To224 OBJECT-TYPE
    SYNTAX INTEGER
    MAX-ACCESS read-only
    STATUS current
    DESCRIPTION     
        "The DC load branch 193 to 224 severe over current alarm.
         The bit0 to bit31 for the receive data means the 
         DC load branch 193 to 224 severe over current alarm status.
         The value 1 means alarm happen for the each bit. 
         And the value of 0 means no alarm for each bit."
    ::= { dcAlarmStatus 23 }
  -- 1.3.6.1.4.1.39553.10.3.2.24
    dcBranchSevereOverCurrentAlarm225To256 OBJECT-TYPE
    SYNTAX INTEGER
    MAX-ACCESS read-only
    STATUS current
    DESCRIPTION     
        "The DC load branch 225 to 256 severe over current alarm.
         The bit0 to bit31 for the receive data means the 
         DC load branch 225 to 256 severe over current alarm status.
         The value 1 means alarm happen for the each bit. 
         And the value of 0 means no alarm for each bit."
    ::= { dcAlarmStatus 24 }
  -- 1.3.6.1.4.1.39553.10.3.2.25
    dcBranchSlightOverCurrentAlarm1To32 OBJECT-TYPE
    SYNTAX INTEGER
    MAX-ACCESS read-only
    STATUS current
    DESCRIPTION     
        "The DC load branch 1 to 32 slight over current alarm.
         The bit0 to bit31 for the receive data means the 
         DC load branch 1 to 32 slight over current alarm status.
         The value 1 means alarm happen for the each bit. 
         And the value of 0 means no alarm for each bit."
    ::= { dcAlarmStatus 25 }
  -- 1.3.6.1.4.1.39553.10.3.2.26
    dcBranchSlightOverCurrentAlarm33To64 OBJECT-TYPE
    SYNTAX INTEGER
    MAX-ACCESS read-only
    STATUS current
    DESCRIPTION     
        "The DC load branch 33 to 64 slight over current alarm.
         The bit0 to bit31 for the receive data means the 
         DC load branch 33 to 64 slight over current alarm status.
         The value 1 means alarm happen for the each bit. 
         And the value of 0 means no alarm for each bit."
    ::= { dcAlarmStatus 26 }
  -- 1.3.6.1.4.1.39553.10.3.2.27
    dcBranchSlightOverCurrentAlarm65To96 OBJECT-TYPE
    SYNTAX INTEGER
    MAX-ACCESS read-only
    STATUS current
    DESCRIPTION     
        "The DC load branch 65 to 96 slight over current alarm.
         The bit0 to bit31 for the receive data means the 
         DC load branch 65 to 96 slight over current alarm status.
         The value 1 means alarm happen for the each bit. 
         And the value of 0 means no alarm for each bit."
    ::= { dcAlarmStatus 27 }
  -- 1.3.6.1.4.1.39553.10.3.2.28
    dcBranchSlightOverCurrentAlarm97To128 OBJECT-TYPE
    SYNTAX INTEGER
    MAX-ACCESS read-only
    STATUS current
    DESCRIPTION     
        "The DC load branch 97 to 128 slight over current alarm.
         The bit0 to bit31 for the receive data means the 
         DC load branch 97 to 128 slight over current alarm status.
         The value 1 means alarm happen for the each bit. 
         And the value of 0 means no alarm for each bit."
    ::= { dcAlarmStatus 28 }
  -- 1.3.6.1.4.1.39553.10.3.2.29
    dcBranchSlightOverCurrentAlarm129To160 OBJECT-TYPE
    SYNTAX INTEGER
    MAX-ACCESS read-only
    STATUS current
    DESCRIPTION     
        "The DC load branch 129 to 160 slight over current alarm.
         The bit0 to bit31 for the receive data means the 
         DC load branch 129 to 160 slight over current alarm status.
         The value 1 means alarm happen for the each bit. 
         And the value of 0 means no alarm for each bit."
    ::= { dcAlarmStatus 29 }
  -- 1.3.6.1.4.1.39553.10.3.2.30
    dcBranchSlightOverCurrentAlarm161To192 OBJECT-TYPE
    SYNTAX INTEGER
    MAX-ACCESS read-only
    STATUS current
    DESCRIPTION     
        "The DC load branch 161 to 192 slight over current alarm.
         The bit0 to bit31 for the receive data means the 
         DC load branch 161 to 192 slight over current alarm status.
         The value 1 means alarm happen for the each bit. 
         And the value of 0 means no alarm for each bit."
    ::= { dcAlarmStatus 30 }
  -- 1.3.6.1.4.1.39553.10.3.2.31
    dcBranchSlightOverCurrentAlarm193To224 OBJECT-TYPE
    SYNTAX INTEGER
    MAX-ACCESS read-only
    STATUS current
    DESCRIPTION     
        "The DC load branch 193 to 224 slight over current alarm.
         The bit0 to bit31 for the receive data means the 
         DC load branch 193 to 224 slight over current alarm status.
         The value 1 means alarm happen for the each bit. 
         And the value of 0 means no alarm for each bit."
    ::= { dcAlarmStatus 31 }
  -- 1.3.6.1.4.1.39553.10.3.2.32
    dcBranchSlightOverCurrentAlarm225To256 OBJECT-TYPE
    SYNTAX INTEGER
    MAX-ACCESS read-only
    STATUS current
    DESCRIPTION     
        "The DC load branch 225 to 256 slight over current alarm.
         The bit0 to bit31 for the receive data means the 
         DC load branch 225 to 256 slight over current alarm status.
         The value 1 means alarm happen for the each bit. 
         And the value of 0 means no alarm for each bit."
    ::= { dcAlarmStatus 32 }
  -- 1.3.6.1.4.1.39553.10.3.2.33
    batteryFuseAlarm1To32 OBJECT-TYPE
    SYNTAX INTEGER
    MAX-ACCESS read-only
    STATUS current
    DESCRIPTION     
        "The battery fuse 1 to 32 break alarm.
         The bit0 to bit31 for the receive data means the 
         battery fuse 1 to 32 break alarm status.
         The value 1 means alarm happen for the each bit. 
         And the value of 0 means no alarm for each bit."
    ::= { dcAlarmStatus 33 }
  -- 1.3.6.1.4.1.39553.10.3.2.34
    batteryFuseNegativeAlarm1To32 OBJECT-TYPE
    SYNTAX INTEGER
    MAX-ACCESS read-only
    STATUS current
    DESCRIPTION     
        "The battery negative fuse 1 to 32 break alarm.
         The bit0 to bit31 for the receive data means the 
         battery negative fuse 1 to 32 break alarm status.
         The value 1 means alarm happen for the each bit. 
         And the value of 0 means no alarm for each bit."
    ::= { dcAlarmStatus 34 }
  -- 1.3.6.1.4.1.39553.10.3.2.35
    digitalInputAlarm1To32 OBJECT-TYPE
    SYNTAX INTEGER
    MAX-ACCESS read-only
    STATUS current
    DESCRIPTION     
        "The digital input 1 to 32 alarm.
         The bit0 to bit31 for the receive data means the 
         digital input 1 to 32 alarm status.
         The value 1 means alarm happen for the each bit. 
         And the value of 0 means no alarm for each bit."
    ::= { dcAlarmStatus 35 }
  -- 1.3.6.1.4.1.39553.10.3.2.36
    digitalInputAlarm33To64 OBJECT-TYPE
    SYNTAX INTEGER
    MAX-ACCESS read-only
    STATUS current
    DESCRIPTION     
        "The digital input 33 to 64 alarm.
         The bit0 to bit31 for the receive data means the 
         digital input 33 to 64 alarm status.
         The value 1 means alarm happen for the each bit. 
         And the value of 0 means no alarm for each bit."
    ::= { dcAlarmStatus 36 }
  -- 1.3.6.1.4.1.39553.10.3.2.43
    dcSystemAlarm OBJECT-TYPE
    SYNTAX INTEGER
    MAX-ACCESS read-only
    STATUS current
    DESCRIPTION     
        "The alarm for DC system.
         The bit0 to bit31 for the receive data means the DC system alarm status.
         The value 1 means alarm happen for the each bit. 
         And the value of 0 means no alarm for each bit.
         bit0 = dcOverVoltage,
         bit1 = dcHighVoltage,
         bit2 = dcLowVoltage,
         bit3 = dcUnderVoltage,
         bit4 = dcLoadBranchSevereOverCurrent,
         bit5 = dcLoadBranchSlightOverCurrent,   
         bit6 = ecoRunning,
         bit7 = busInsulationFault,
         bit8 = loadBranchInsulationFault,
         bit9 = dcTotalLoadSlightOverCurrent,
         bit10 = dcTotalLoadSevereOverCurrent,
         bit11 = systemSPDFault,
         bit12 = systemTotalAlarm,
         bit13-bit31 = Reserve."
    ::= { dcAlarmStatus 43 }
  -- 1.3.6.1.4.1.39553.10.3.2.44
    batteryAlarm OBJECT-TYPE
    SYNTAX INTEGER
    MAX-ACCESS read-only
    STATUS current
    DESCRIPTION     
        "The alarm for battery.
         The bit0 to bit31 for the receive data means the battery alarm status.
         The value 1 means alarm happen for the each bit. 
         And the value of 0 means no alarm for each bit.
         bit0 = batteryChargeOverCurrent,
         bit1 = batteryDischarge,
         bit2 = batteryQuickTestOverCurrent,
         bit3 = battery1MiddleImbalance,
         bit4 = battery2MiddleImbalance,
         bit5 = battery3MiddleImbalance,
         bit6 = battery4MiddleImbalance,
         bit7 = battery5MiddleImbalance,
         bit8 = battery6MiddleImbalance,
         bit9 = battery7MiddleImbalance,
         bit10 = battery8MiddleImbalance,
         bit11 = battery1CanNotCharge,
         bit12 = battery2CanNotCharge,
         bit13 = battery3CanNotCharge,
         bit14 = battery4CanNotCharge,
         bit15 = battery5CanNotCharge,
         bit16 = battery6CanNotCharge,
         bit17 = battery7CanNotCharge,
         bit18 = battery8CanNotCharge,
         bit19 = batteryTestFail,
         bit20-bit31 = Reserve."
    ::= { dcAlarmStatus 44 }
  -- 1.3.6.1.4.1.39553.10.3.2.45
    communicationAlarmGroup1 OBJECT-TYPE
    SYNTAX INTEGER
    MAX-ACCESS read-only
    STATUS current
    DESCRIPTION     
        "The alarm for communication group 1.
         The bit0 to bit31 for the receive data means the communication group 1 alarm status.
         The value 1 means alarm happen for the each bit. 
         And the value of 0 means no alarm for each bit.
         bit0 = sc210-1CommunicationFault,
         bit1 = sc210-2CommunicationFault,
         bit2 = sc501-1CommunicationFault,
         bit3 = sc501-2CommunicationFault,
         bit4 = sc501-3CommunicationFault,
         bit5 = sc501-4CommunicationFault,
         bit6 = sc310-1CommunicationFault,
         bit7 = sc310-2CommunicationFault,
         bit8 = sc310-3CommunicationFault,
         bit9 = sc340-1CommunicationFault,
         bit10 = sc340-2CommunicationFault,
         bit11 = sc340-3CommunicationFault,
         bit12 = sc200-1CommunicationFault,
         bit13 = sc200-2CommunicationFault,
         bit14 = sc200-3CommunicationFault,
         bit15 = sc920-1CommunicationFault,
         bit16 = sc920-2CommunicationFault,
         bit17 = sc320-1CommunicationFault,
         bit18 = sc320-2CommunicationFault,
         bit19 = sc320-3CommunicationFault,
         bit20 = sc320-4CommunicationFault,
         bit21 = sc320-5CommunicationFault,
         bit22 = sc330-1CommunicationFault,
         bit23 = sc330-2CommunicationFault,
         bit24 = sc330-3CommunicationFault,
         bit25 = sc330-4CommunicationFault,
         bit26 = sc330-5CommunicationFault,
         bit27 = sc930-1CommunicationFault,
         bit28 = sc930-2CommunicationFault,
         bit29 = sc900-1CommunicationFault,
         bit30 = sc900-2CommunicationFault,
         bit31 = sc900-3CommunicationFault."
    ::= { dcAlarmStatus 45 }
  -- 1.3.6.1.4.1.39553.10.3.2.46
    communicationAlarmGroup2 OBJECT-TYPE
    SYNTAX INTEGER
    MAX-ACCESS read-only
    STATUS current
    DESCRIPTION
        "The alarm for communication group 2.
         The bit0 to bit31 for the receive data means the communication group 2 alarm status.
         The value 1 means alarm happen for the each bit. 
         And the value of 0 means no alarm for each bit.
         bit0 = sc900-4CommunicationFault,
         bit1 = bms1CommunicationFault,
         bit2 = bms2CommunicationFault,
         bit3 = bms3CommunicationFault,
         bit4 = bms4CommunicationFault,
         bit5 = bms5CommunicationFault,
         bit6 = bms6CommunicationFault,
         bit7 = bms7CommunicationFault,
         bit8 = bms8CommunicationFault,
         bit9 = bms9CommunicationFault,
         bit10 = bms10CommunicationFault,
         bit11 = bms11CommunicationFault,
         bit12 = bms12CommunicationFault,
         bit13 = bms13CommunicationFault,
         bit14 = bms14CommunicationFault,
         bit15 = bms15CommunicationFault,
         bit16 = bms16CommunicationFault,
         bit17 = bms17CommunicationFault,
         bit18 = bms18CommunicationFault,
         bit19 = bms19CommunicationFault,
         bit20 = bms20CommunicationFault,
         bit21 = temperatureSensor1NotAssemble,
         bit22 = temperatureSensor2NotAssemble,
         bit23 = extendTemperatureSensor1NotAssemble,
         bit24 = extendTemperatureSensor2NotAssemble,
         bit25-bit31 = Reserve."
    ::= { dcAlarmStatus 46 }
  -- 1.3.6.1.4.1.39553.10.3.2.47
    lvdAlarm OBJECT-TYPE
    SYNTAX INTEGER
    MAX-ACCESS read-only
    STATUS current
    DESCRIPTION
        "The alarm for LVD.
         The bit0 to bit31 for the receive data means the LVD alarm status.
         The value 1 means alarm happen for the each bit. 
         And the value of 0 means no alarm for each bit.
         bit0 = lLVD1,
         bit1 = lLVD2,
         bit2 = lLVD3,
         bit3 = lLVD4,
         bit4 = lLVD5,
         bit5 = lLVD6,
         bit6 = lLVD7,
         bit7 = lLVD8,
         bit8 = bLVD,
         bit9 = lLVD1Fail,
         bit10 = lLVD2Fail,
         bit11 = lLVD3Fail,
         bit12 = lLVD4Fail,
         bit13 = lLVD5Fail,
         bit14 = lLVD6Fail,
         bit15 = lLVD7Fail,
         bit16 = lLVD8Fail,
         bit17 = bLVDFail,
         bit18 = preAlarmlLVD1,
         bit19 = preAlarmlLVD2,
         bit20 = preAlarmlLVD3,
         bit21 = preAlarmlLVD4,
         bit22 = preAlarmlLVD5,
         bit23 = preAlarmlLVD6,
         bit24 = preAlarmlLVD7,
         bit25 = preAlarmlLVD8,
         bit26 = preAlarmbLVD,
         bit27-bit31 = Reserve."
    ::= { dcAlarmStatus 47 }
  -- 1.3.6.1.4.1.39553.10.3.2.48
        batteryTemperatureAlarm OBJECT-TYPE
        SYNTAX INTEGER
        MAX-ACCESS read-only
        STATUS current
        DESCRIPTION
        "The alarm for battery temperature.
         The bit0 to bit31 for the receive data means the battery temperature alarm status.
         The value 1 means alarm happen for the each bit. 
         And the value of 0 means no alarm for each bit.
         bit0 = batteryTemperature1High1,
         bit1 = batteryTemperature2High1,
         bit2 = batteryTemperature3High1,
         bit3 = batteryTemperature4High1,
         bit4 = batteryTemperature5High1,
         bit5 = batteryTemperature6High1,
         bit6 = batteryTemperature7High1,
         bit7 = batteryTemperature8High1,
         bit8 = batteryTemperature1High2,
         bit9 = batteryTemperature2High2,
         bit10 = batteryTemperature3High2,
         bit11 = batteryTemperature4High2,
         bit12 = batteryTemperature5High2,
         bit13 = batteryTemperature6High2,
         bit14 = batteryTemperature7High2,
         bit15 = batteryTemperature8High2,
         bit16 = batteryTemperature1Low1,
         bit17 = batteryTemperature2Low1,
         bit18 = batteryTemperature3Low1,
         bit19 = batteryTemperature4Low1,
         bit20 = batteryTemperature5Low1,
         bit21 = batteryTemperature6Low1,
         bit22 = batteryTemperature7Low1,
         bit23 = batteryTemperature8Low1,
         bit24 = batteryTemperature1Low2,
         bit25 = batteryTemperature2Low2,
         bit26 = batteryTemperature3Low2,
         bit27 = batteryTemperature4Low2,
         bit28 = batteryTemperature5Low2,
         bit29 = batteryTemperature6Low2,
         bit30 = batteryTemperature7Low2,
         bit31 = batteryTemperature8Low2."
        ::= { dcAlarmStatus 48 }
  -- 1.3.6.1.4.1.39553.10.3.2.49
    ambientTemperatureAlarm OBJECT-TYPE
    SYNTAX INTEGER
    MAX-ACCESS read-only
    STATUS current
    DESCRIPTION
        "The alarm for ambient temperature.
         The bit0 to bit31 for the receive data means the ambient temperature alarm status.
         The value 1 means alarm happen for the each bit. 
         And the value of 0 means no alarm for each bit.
         bit0 = ambientTemperature1High1,
         bit1 = ambientTemperature2High1,
         bit2 = ambientTemperature3High1,
         bit3 = ambientTemperature4High1,
         bit4 = ambientTemperature5High1,
         bit5 = ambientTemperature6High1,
         bit6 = ambientTemperature7High1,
         bit7 = ambientTemperature8High1,
         bit8 = ambientTemperature1High2,
         bit9 = ambientTemperature2High2,
         bit10 = ambientTemperature3High2,
         bit11 = ambientTemperature4High2,
         bit12 = ambientTemperature5High2,
         bit13 = ambientTemperature6High2,
         bit14 = ambientTemperature7High2,
         bit15 = ambientTemperature8High2,
         bit16 = ambientTemperature1Low1,
         bit17 = ambientTemperature2Low1,
         bit18 = ambientTemperature3Low1,
         bit19 = ambientTemperature4Low1,
         bit20 = ambientTemperature5Low1,
         bit21 = ambientTemperature6Low1,
         bit22 = ambientTemperature7Low1,
         bit23 = ambientTemperature8Low1,
         bit24 = ambientTemperature1Low2,
         bit25 = ambientTemperature2Low2,
         bit26 = ambientTemperature3Low2,
         bit27 = ambientTemperature4Low2,
         bit28 = ambientTemperature5Low2,
         bit29 = ambientTemperature6Low2,
         bit30 = ambientTemperature7Low2,
         bit31 = ambientTemperature8Low2."
    ::= { dcAlarmStatus 49 }
  -- 1.3.6.1.4.1.39553.10.3.2.50
    humidityAlarm OBJECT-TYPE
    SYNTAX INTEGER
    MAX-ACCESS read-only
    STATUS current
    DESCRIPTION
        "The alarm for humidity.
         The bit0 to bit31 for the receive data means the humidity alarm status.
         The value 1 means alarm happen for the each bit. 
         And the value of 0 means no alarm for each bit.
         bit0 = humidityHigh,
         bit1 = humidityLow,
         bit2-bit31 = Reserve."
    ::= { dcAlarmStatus 50 }
    -- 1.3.6.1.4.1.39553.10.3.2.51
    batteryTemperatureAlarm2 OBJECT-TYPE
    SYNTAX INTEGER
    MAX-ACCESS read-only
    STATUS current
    DESCRIPTION
        "The battery temperature alarm group 2.
         The bit0 to bit31 for the receive data means the battery temperature alarm group 2 status.
         The value 1 means alarm happen for the each bit. 
         And the value of 0 means no alarm for each bit.
         bit0 = bTRMHigh1,
         bit1 = bTRMHigh2,
         bit2-bit31 = Reserve."
    ::= { dcAlarmStatus 51 }
    -- 1.3.6.1.4.1.39553.10.3.2.52
    bmsAlarm OBJECT-TYPE
    SYNTAX INTEGER
    MAX-ACCESS read-only
    STATUS current
    DESCRIPTION
        "The BMS alarm.
         The bit0 to bit31 for the receive data means the BMS alarm status.
         The value 1 means alarm happen for the each bit. 
         And the value of 0 means no alarm for each bit.
         bit0 = bmsTotalAlarm,
         bit1 = bmsBatteryOverCurrent,
         bit2 = bmsBatteryPacksOverVoltage,
         bit3 = bmsBatteryPacksUnderVoltage,
         bit4 = bmsBatteryCellOverVoltage,
         bit5 = bmsBatteryCellUnderVoltage,
         bit6 = bmsBatteryHighTenmperature,
         bit7 = bmsBatteryLowTenmperature,
         bit8 = bmsBatteryOutputShort,
         bit9 = bmsBatteryLowSOC,
         bit10-bit31 = Reserve."
    ::= { dcAlarmStatus 52 }
    -- 1.3.6.1.4.1.39553.10.3.2.53
    plcArithmeticAlarm1 OBJECT-TYPE
    SYNTAX INTEGER
    MAX-ACCESS read-only
    STATUS current
    DESCRIPTION
        "The PLC arithmetic alarm group 1.
         The bit0 to bit31 for the receive data means the PLC arithmetic alarm group 1 status.
         The value 1 means alarm happen for the each bit. 
         And the value of 0 means no alarm for each bit.
         bit0 = plcArithmetic1Alarm,
         bit1 = plcArithmetic2Alarm,
         bit2 = plcArithmetic3Alarm,
         bit3 = plcArithmetic4Alarm,
         bit4 = plcArithmetic5Alarm,
         bit5 = plcArithmetic6Alarm,
         bit6 = plcArithmetic7Alarm,
         bit7 = plcArithmetic8Alarm,
         bit8 = plcArithmetic9Alarm,
         bit9 = plcArithmetic10Alarm,
         bit10 = plcArithmetic11Alarm,
         bit11 = plcArithmetic12Alarm,
         bit12 = plcArithmetic13Alarm,
         bit13 = plcArithmetic14Alarm,
         bit14 = plcArithmetic15Alarm,
         bit15 = plcArithmetic16Alarm,
         bit16 = plcArithmetic17Alarm,
         bit17 = plcArithmetic18Alarm,
         bit18 = plcArithmetic19Alarm,
         bit19 = plcArithmetic20Alarm,
         bit20 = plcArithmetic21Alarm,
         bit21 = plcArithmetic22Alarm,
         bit22 = plcArithmetic23Alarm,
         bit23 = plcArithmetic24Alarm,
         bit24 = plcArithmetic25Alarm,
         bit25 = plcArithmetic26Alarm,
         bit26 = plcArithmetic27Alarm,
         bit27 = plcArithmetic28Alarm,
         bit28 = plcArithmetic29Alarm,
         bit29 = plcArithmetic30Alarm,
         bit30 = plcArithmetic31Alarm,
         bit31 = plcArithmetic32Alarm."
    ::= { dcAlarmStatus 53 }
    -- 1.3.6.1.4.1.39553.10.3.2.54
    plcArithmeticAlarm2 OBJECT-TYPE
    SYNTAX INTEGER
    MAX-ACCESS read-only
    STATUS current
    DESCRIPTION
        "The PLC arithmetic alarm group 2.
         The bit0 to bit31 for the receive data means the PLC arithmetic alarm group 2 status.
         The value 1 means alarm happen for the each bit. 
         And the value of 0 means no alarm for each bit.
         bit0 = plcArithmetic33Alarm,
         bit1 = plcArithmetic34Alarm,
         bit2 = plcArithmetic35Alarm,
         bit3 = plcArithmetic36Alarm,
         bit4 = plcArithmetic37Alarm,
         bit5 = plcArithmetic38Alarm,
         bit6 = plcArithmetic39Alarm,
         bit7 = plcArithmetic40Alarm,
         bit8-bit31 = Reserve."
    ::= { dcAlarmStatus 54 }
    -- 1.3.6.1.4.1.39553.10.3.2.55
    plcLogicAlarm OBJECT-TYPE
    SYNTAX INTEGER
    MAX-ACCESS read-only
    STATUS current
    DESCRIPTION
        "The PLC logic alarm.
         The bit0 to bit31 for the receive data means the PLC logic alarm status.
         The value 1 means alarm happen for the each bit. 
         And the value of 0 means no alarm for each bit.
         bit0 = plcLogic1Alarm,
         bit1 = plcLogic2Alarm,
         bit2 = plcLogic3Alarm,
         bit3 = plcLogic4Alarm,
         bit4 = plcLogic5Alarm,
         bit5 = plcLogic6Alarm,
         bit6 = plcLogic7Alarm,
         bit7 = plcLogic8Alarm,
         bit8 = plcLogic9Alarm,
         bit9 = plcLogic10Alarm,
         bit10-bit31 = Reserve."
    ::= { dcAlarmStatus 55 }
    -- 1.3.6.1.4.1.39553.10.3.2.56
    plcGroupAlarm OBJECT-TYPE
    SYNTAX INTEGER
    MAX-ACCESS read-only
    STATUS current
    DESCRIPTION
        "The PLC group alarm.
         The bit0 to bit31 for the receive data means the PLC group alarm status.
         The value 1 means alarm happen for the each bit. 
         And the value of 0 means no alarm for each bit.
         bit0 = plcGroup1Alarm,
         bit1 = plcGroup2Alarm,
         bit2 = plcGroup3Alarm,
         bit3 = plcGroup4Alarm,
         bit4 = plcGroup5Alarm,
         bit5 = plcGroup6Alarm,
         bit6 = plcGroup7Alarm,
         bit7 = plcGroup8Alarm,
         bit8 = plcGroup9Alarm,
         bit9 = plcGroup10Alarm,
         bit10 = plcGroup11Alarm,
         bit11 = plcGroup12Alarm,
         bit12 = plcGroup13Alarm,
         bit13 = plcGroup14Alarm,
         bit14 = plcGroup15Alarm,
         bit15 = plcGroup16Alarm,
         bit16 = plcGroup17Alarm,
         bit17 = plcGroup18Alarm,
         bit18 = plcGroup19Alarm,
         bit19 = plcGroup20Alarm,
         bit20 = plcGroup21Alarm,
         bit21 = plcGroup22Alarm,
         bit22 = plcGroup23Alarm,
         bit23 = plcGroup24Alarm,
         bit24 = plcGroup25Alarm,
         bit25 = plcGroup26Alarm,
         bit26 = plcGroup27Alarm,
         bit27 = plcGroup28Alarm,
         bit28 = plcGroup29Alarm,
         bit29 = plcGroup30Alarm,
         bit30-bit31 = Reserve."
    ::= { dcAlarmStatus 56 }
    -- 1.3.6.1.4.1.39553.10.3.2.57
    communicationAlarmGroup3 OBJECT-TYPE
    SYNTAX INTEGER
    MAX-ACCESS read-only
    STATUS current
    DESCRIPTION
        "The alarm for communication group 3.
         The bit0 to bit31 for the receive data means the communication group 2 alarm status.
         The value 1 means alarm happen for the each bit. 
         And the value of 0 means no alarm for each bit.
         bit0 =     bmm1CommunicationFault,
        bit1 =  bmm2CommunicationFault,
        bit2 =  bmm3CommunicationFault,
        bit3 =  bmm4CommunicationFault,
        bit4 =  bmm5CommunicationFault,
        bit5 =  bmm6CommunicationFault,
        bit6 =  bmm7CommunicationFault,
        bit7 =  bmm8CommunicationFault,
        bit8 =  bmm9CommunicationFault,
        bit9 =  bmm10CommunicationFault,
        bit10 = DG1 CommunicationFault,
        bit11 = DG2 CommunicationFault,
        bit12 = DG3 CommunicationFault,
        bit13 = EXT 2 temperature sensor 1 fault,
        bit14 = EXT 2 temperature sensor 2 fault,
        bit15 = EXT 3 temperature sensor 1 fault,
        bit16 = EXT 3 temperature sensor 2 fault,
        bit17 = EXT 4 temperature sensor 1 fault,
        bit18 = EXT 4 temperature sensor 2 fault,
        bit19 = EXT 5 temperature sensor 1 fault,
        bit20 = EXT 5 temperature sensor 2 fault,
        bit21 = SC350 1 CommunicationFault,
        bit22 = SC350 2 CommunicationFault,
        bit23 = SC350 3 CommunicationFault,
        bit24 = SC360 CommunicationFault,
         bit25-bit31 = Reserve."
    ::= { dcAlarmStatus 57 }
------------------------------------------------------------
-- System Parameter Setting{ dcDistribution 4 }
------------------------------------------------------------        
  -- 1.3.6.1.4.1.39553.10.3.4
    systemParameter OBJECT IDENTIFIER ::= { dcDistribution 4 }

  -- 1.3.6.1.4.1.39553.10.3.4.1
    timeZone OBJECT-TYPE
    SYNTAX INTEGER (0..36)
    MAX-ACCESS read-write
    STATUS current
    DESCRIPTION 
        "System time zone."
    ::= { systemParameter 1 }
  -- 1.3.6.1.4.1.39553.10.3.4.2
    timeFormat OBJECT-TYPE
    SYNTAX INTEGER {
        yearMonthDay (0),
        monthDayYear (1),
        dayMonthYear (2)
    }
    MAX-ACCESS read-write
    STATUS current
    DESCRIPTION 
        "System time display format.
         0=Y-M-D;
         1=M-D-Y;
         2=D-M-Y."
    ::= { systemParameter 2 }
  -- 1.3.6.1.4.1.39553.10.3.4.3
    dcCabinetNumber OBJECT-TYPE
    SYNTAX INTEGER (0..255)
    MAX-ACCESS read-write
    STATUS current
    DESCRIPTION 
        "DC cabinet number."
    ::= { systemParameter 3 }
  -- 1.3.6.1.4.1.39553.10.3.4.4
    systemVoltageLevel OBJECT-TYPE
    SYNTAX INTEGER {
        level48V (0),
        level24V (1),
        level336V (2),
        level240V (3),
        level500V (4),
        level750V (5)
    }
    MAX-ACCESS read-write
    STATUS current
    DESCRIPTION 
        "System current voltage level.
        0=48V,
        1=24V,
        2=336V,
        3=240V,
        4=500V,
        5=750V."
    ::= { systemParameter 4 }
  -- 1.3.6.1.4.1.39553.10.3.4.5
    ipAddress OBJECT-TYPE
    SYNTAX IpAddress
    MAX-ACCESS read-write
    STATUS current
    DESCRIPTION 
        "The controller's IP addresss."
    ::= { systemParameter 5 }
  -- 1.3.6.1.4.1.39553.10.3.4.6
    subnetMask OBJECT-TYPE
    SYNTAX IpAddress
    MAX-ACCESS read-write
    STATUS current
    DESCRIPTION 
        "The controller's subnet Mask."
    ::= { systemParameter 6 }
  -- 1.3.6.1.4.1.39553.10.3.4.7
    defaultGateway OBJECT-TYPE
    SYNTAX IpAddress
    MAX-ACCESS read-write
    STATUS current
    DESCRIPTION 
        "The controller's default gateway."
    ::= { systemParameter 7 }
  -- 1.3.6.1.4.1.39553.10.3.4.8
    sci0Address OBJECT-TYPE
    SYNTAX INTEGER (0..255)
    MAX-ACCESS read-write
    STATUS current
    DESCRIPTION 
        "The serial communication interface 0 addresss."
    ::= { systemParameter 8 }
  -- 1.3.6.1.4.1.39553.10.3.4.9
    sci1Address OBJECT-TYPE
    SYNTAX INTEGER (0..255)
    MAX-ACCESS read-write
    STATUS current
    DESCRIPTION 
        "The serial communication interface 1 addresss."
    ::= { systemParameter 9 }
  -- 1.3.6.1.4.1.39553.10.3.4.10
    sci2Address OBJECT-TYPE
    SYNTAX INTEGER (0..255)
    MAX-ACCESS read-write
    STATUS current
    DESCRIPTION 
        "The serial communication interface 2 addresss."
    ::= { systemParameter 10 }
  -- 1.3.6.1.4.1.39553.10.3.4.11
    sci3Address OBJECT-TYPE
    SYNTAX INTEGER (0..255)
    MAX-ACCESS read-write
    STATUS current
    DESCRIPTION 
        "The serial communication interface 3 addresss."
    ::= { systemParameter 11 }
  -- 1.3.6.1.4.1.39553.10.3.4.12
    sci4Address OBJECT-TYPE
    SYNTAX INTEGER (0..255)
    MAX-ACCESS read-write
    STATUS current
    DESCRIPTION 
        "The serial communication interface 4 addresss."
    ::= { systemParameter 12 }
  -- 1.3.6.1.4.1.39553.10.3.4.13
    sci5Address OBJECT-TYPE
    SYNTAX INTEGER
    MAX-ACCESS read-write
    STATUS current
    DESCRIPTION 
        "The serial communication interface 5 addresss."
    ::= { systemParameter 13 }
  -- 1.3.6.1.4.1.39553.10.3.4.14
    sci6Address OBJECT-TYPE
    SYNTAX INTEGER
    MAX-ACCESS read-write
    STATUS current
    DESCRIPTION 
        "The serial communication interface 6 addresss."
    ::= { systemParameter 14 }
  -- 1.3.6.1.4.1.39553.10.3.4.15
    sci0Parity OBJECT-TYPE
    SYNTAX INTEGER {
        none (0),
        odd (1),
        even (2)
    }
    MAX-ACCESS read-write
    STATUS current
    DESCRIPTION 
        "The serial communication interface 0 parity bit."
    ::= { systemParameter 15 }
  -- 1.3.6.1.4.1.39553.10.3.4.16
    sci1Parity OBJECT-TYPE
    SYNTAX INTEGER {
        none (0),
        odd (1),
        even (2)
    }
    MAX-ACCESS read-write
    STATUS current
    DESCRIPTION 
        "The serial communication interface 1 parity bit."
    ::= { systemParameter 16 }
  -- 1.3.6.1.4.1.39553.10.3.4.17
    sci2Parity OBJECT-TYPE
    SYNTAX INTEGER {
        none (0),
        odd (1),
        even (2)
    }
    MAX-ACCESS read-write
    STATUS current
    DESCRIPTION 
        "The serial communication interface 2 parity bit."
    ::= { systemParameter 17 }
  -- 1.3.6.1.4.1.39553.10.3.4.18
    sci3Parity OBJECT-TYPE
    SYNTAX INTEGER {
        none (0),
        odd (1),
        even (2)
    }
    MAX-ACCESS read-write
    STATUS current
    DESCRIPTION 
        "The serial communication interface 3 parity bit."
    ::= { systemParameter 18 }
  -- 1.3.6.1.4.1.39553.10.3.4.19
    sci4Parity OBJECT-TYPE
    SYNTAX INTEGER {
        none (0),
        odd (1),
        even (2)
    }
    MAX-ACCESS read-write
    STATUS current
    DESCRIPTION 
        "The serial communication interface 4 parity bit."
    ::= { systemParameter 19 }
  -- 1.3.6.1.4.1.39553.10.3.4.20
    sci5Parity OBJECT-TYPE
    SYNTAX INTEGER {
        none (0),
        odd (1),
        even (2)
    }
    MAX-ACCESS read-write
    STATUS current
    DESCRIPTION 
        "The serial communication interface 5 parity bit."
    ::= { systemParameter 20 }
  -- 1.3.6.1.4.1.39553.10.3.4.21
    sci6Parity OBJECT-TYPE
    SYNTAX INTEGER {
        none (0),
        odd (1),
        even (2)
    }
    MAX-ACCESS read-write
    STATUS current
    DESCRIPTION 
        "The serial communication interface 6 parity bit."
    ::= { systemParameter 21 }
  -- 1.3.6.1.4.1.39553.10.3.4.22
    sci0BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 0 baud rate."
    ::= { systemParameter 22 }
  -- 1.3.6.1.4.1.39553.10.3.4.23
    sci1BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 1 baud rate."
    ::= { systemParameter 23 }
  -- 1.3.6.1.4.1.39553.10.3.4.24
    sci2BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 2 baud rate."
    ::= { systemParameter 24 }
  -- 1.3.6.1.4.1.39553.10.3.4.25
    sci3BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 3 baud rate."
    ::= { systemParameter 25 }
  -- 1.3.6.1.4.1.39553.10.3.4.26
    sci4BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 4 baud rate."
    ::= { systemParameter 26 }
  -- 1.3.6.1.4.1.39553.10.3.4.27
    sci5BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 5 baud rate."
    ::= { systemParameter 27 }
  -- 1.3.6.1.4.1.39553.10.3.4.28
    sci6BaudRate OBJECT-TYPE
    SYNTAX INTEGER {
        rate110bps (0),
        rate300bps (1),
        rate600bps (2),
        rate1200bps (3),
        rate2400bps (4),
        rate4800bps (5),
        rate9600bps (6),
        rate14400bps (7),
        rate19200bps (8),
        rate38400bps (9),
        rate56000bps (10),
        rate57600bps (11),
        rate115200bps (12),
        rate128000bps (13),
        rate256000bps (14)
    }
    MAX-ACCESS read-write
    STATUS current
    DESCRIPTION 
        "The serial communication interface 6 baud rate."
    ::= { systemParameter 28 }
  -- 1.3.6.1.4.1.39553.10.3.4.29
    sci0Protocol OBJECT-TYPE
    SYNTAX INTEGER {
        modbus (0),
        ydn23 (1),
        richPowerBMS (2),
        bmm (3),
        modbusHost (4),
        amf25 (5),
        dse7320 (6)
        
    }
    MAX-ACCESS read-write
    STATUS current
    DESCRIPTION 
        "The serial communication interface 0 protocol type."
    ::= { systemParameter 29 }
  -- 1.3.6.1.4.1.39553.10.3.4.30
    sci1Protocol OBJECT-TYPE
    SYNTAX INTEGER {
        modbus (0),
        ydn23 (1),
        richPowerBMS (2),
        bmm (3),
        modbusHost (4),
        amf25 (5),
        dse7320 (6)
    }
    MAX-ACCESS read-write
    STATUS current
    DESCRIPTION 
        "The serial communication interface 1 protocol type."
    ::= { systemParameter 30 }
  -- 1.3.6.1.4.1.39553.10.3.4.31
    sci2Protocol OBJECT-TYPE
    SYNTAX INTEGER {
        modbus (0),
        ydn23 (1),
        richPowerBMS (2),
        bmm (3),
        modbusHost (4),
        amf25 (5),
        dse7320 (6)
    }
    MAX-ACCESS read-write
    STATUS current
    DESCRIPTION 
        "The serial communication interface 2 protocol type."
    ::= { systemParameter 31 }
  -- 1.3.6.1.4.1.39553.10.3.4.32
    sci3Protocol OBJECT-TYPE
    SYNTAX INTEGER {
        modbus (0),
        ydn23 (1),
        richPowerBMS (2),
        bmm (3),
        modbusHost (4),
        amf25 (5),
        dse7320 (6)
    }
    MAX-ACCESS read-write
    STATUS current
    DESCRIPTION 
        "The serial communication interface 3 protocol type."
    ::= { systemParameter 32 }
  -- 1.3.6.1.4.1.39553.10.3.4.33
    sci4Protocol OBJECT-TYPE
    SYNTAX INTEGER {
        modbus (0),
        ydn23 (1),
        richPowerBMS (2),
        bmm (3),
        modbusHost (4),
        amf25 (5),
        dse7320 (6)
    }
    MAX-ACCESS read-write
    STATUS current
    DESCRIPTION 
        "The serial communication interface 4 protocol type."
    ::= { systemParameter 33 }
  -- 1.3.6.1.4.1.39553.10.3.4.34
    sci5Protocol OBJECT-TYPE
    SYNTAX INTEGER {
        modbus (0),
        ydn23 (1),
        richPowerBMS (2),
        bmm (3),
        modbusHost (4),
        amf25 (5),
        dse7320 (6)
    }
    MAX-ACCESS read-write
    STATUS current
    DESCRIPTION 
        "The serial communication interface 5 protocol type."
    ::= { systemParameter 34 }
  -- 1.3.6.1.4.1.39553.10.3.4.35
    sci6Protocol OBJECT-TYPE
    SYNTAX INTEGER {
        modbus (0),
        ydn23 (1),
        richPowerBMS (2),
        bmm (3),
        modbusHost (4),
        amf25 (5),
        dse7320 (6)
    }
    MAX-ACCESS read-write
    STATUS current
    DESCRIPTION 
        "The serial communication interface 6 protocol type."
    ::= { systemParameter 35 }
  -- 1.3.6.1.4.1.39553.10.3.4.36
    acCabinetNumber OBJECT-TYPE
    SYNTAX INTEGER (0..2)
    MAX-ACCESS read-write
    STATUS current
    DESCRIPTION 
        "The AC distribution cabinet number."
    ::= { systemParameter 36 }
  -- 1.3.6.1.4.1.39553.10.3.4.37
    engineerPassWord OBJECT-TYPE
    SYNTAX DisplayString (SIZE(0..8))
    MAX-ACCESS read-write
    STATUS current
    DESCRIPTION 
        "The engineer pass word."
    ::= { systemParameter 37 }
  -- 1.3.6.1.4.1.39553.10.3.4.38
    administratorPassWord OBJECT-TYPE
    SYNTAX DisplayString (SIZE(0..8))
    MAX-ACCESS read-write
    STATUS current
    DESCRIPTION 
        "The administrator pass word."
    ::= { systemParameter 38 }
  -- 1.3.6.1.4.1.39553.10.3.4.40
    longitudeZone OBJECT-TYPE
    SYNTAX INTEGER {
        eastlongitude (0),
        westlongitude (1)
    }
    MAX-ACCESS read-write
    STATUS current
    DESCRIPTION 
        "The longitude zone.
        0 = eastLongitude,
        1 = westLongitude."
    ::= { systemParameter 40 }
  -- 1.3.6.1.4.1.39553.10.3.4.41
    latitudeZone OBJECT-TYPE
    SYNTAX INTEGER {
        southLatitude(0),
        northLatitude(1)
    }
    MAX-ACCESS read-write
    STATUS current
    DESCRIPTION 
        "The latitude zone.
        0 = southLatitude,
        1 = northLatitude."
    ::= { systemParameter 41 }
  -- 1.3.6.1.4.1.39553.10.3.4.42
    longitudeDegree OBJECT-TYPE
    SYNTAX INTEGER (0..180)
    MAX-ACCESS read-write
    STATUS current
    DESCRIPTION 
        "The longitude degree."
    ::= { systemParameter 42 }
  -- 1.3.6.1.4.1.39553.10.3.4.43
    longitudeMinute OBJECT-TYPE
    SYNTAX INTEGER (0..60)
    MAX-ACCESS read-write
    STATUS current
    DESCRIPTION 
        "The longitude minute."
    ::= { systemParameter 43 }
  -- 1.3.6.1.4.1.39553.10.3.4.44
    longitudeSecond OBJECT-TYPE
    SYNTAX INTEGER (0..60)
    MAX-ACCESS read-write
    STATUS current
    DESCRIPTION 
        "The longitude second."
    ::= { systemParameter 44 }
  -- 1.3.6.1.4.1.39553.10.3.4.45
    latitudeDegree OBJECT-TYPE
    SYNTAX INTEGER (0..180)
    MAX-ACCESS read-write
    STATUS current
    DESCRIPTION 
        "The latitude degree."
    ::= { systemParameter 45 }
  -- 1.3.6.1.4.1.39553.10.3.4.46
    latitudeMinute OBJECT-TYPE
    SYNTAX INTEGER (0..60)
    MAX-ACCESS read-write
    STATUS current
    DESCRIPTION 
        "The latitude minute."
    ::= { systemParameter 46 }
  -- 1.3.6.1.4.1.39553.10.3.4.47
    latitudeSecond OBJECT-TYPE
    SYNTAX INTEGER (0..60)
    MAX-ACCESS read-write
    STATUS current
    DESCRIPTION 
        "The latitude second."
    ::= { systemParameter 47 }
  -- 1.3.6.1.4.1.39553.10.3.4.49
    temperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The temperature sensor 1 configuration."
    ::= { systemParameter 49 }
  -- 1.3.6.1.4.1.39553.10.3.4.50
    temperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The temperature sensor 2 configuration."
    ::= { systemParameter 50 }
  -- 1.3.6.1.4.1.39553.10.3.4.51
    extendTemperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The temperature extend sensor 1 configuration."
    ::= { systemParameter 51 }
  -- 1.3.6.1.4.1.39553.10.3.4.52
    extendTemperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The temperature extend sensor 2 configuration."
    ::= { systemParameter 52 }

  -- 1.3.6.1.4.1.39553.10.3.4.57
    humiditySensorConfiguration OBJECT-TYPE
    SYNTAX INTEGER {
        none (0),
        ambient1 (1),
        ambient2 (2),
        ambient3 (3),
        ambient4 (4),
        ambient5 (5)
    }
    MAX-ACCESS read-write
    STATUS current
    DESCRIPTION 
        "The humidity sensor configuration."
    ::= { systemParameter 57 }
  -- 1.3.6.1.4.1.39553.10.3.4.58
    humiditySensorType OBJECT-TYPE
    SYNTAX INTEGER {
        current (0),
        voltage (1),
        fuelLevelType1 (2),
        fuelLevelType2 (3)
    }
    MAX-ACCESS read-write
    STATUS current
    DESCRIPTION 
        "The humidity sensor type."
    ::= { systemParameter 58 }
  -- 1.3.6.1.4.1.39553.10.3.4.59
    humidityMinimumValue OBJECT-TYPE
    SYNTAX INTEGER (-4000..10000)
    MAX-ACCESS read-write
    STATUS current
    DESCRIPTION 
        "The lower limit for the humidity sensor sample range.
        The actual value = The set or receive data / 100."
    ::= { systemParameter 59 }
  -- 1.3.6.1.4.1.39553.10.3.4.60
    humidityMaximumValue OBJECT-TYPE
    SYNTAX INTEGER (-4000..10000)
    MAX-ACCESS read-write
    STATUS current
    DESCRIPTION 
        "The upper limit for the humidity sensor sample range.
        The actual value = The set or receive data / 100."
    ::= { systemParameter 60 }
  -- 1.3.6.1.4.1.39553.10.3.4.61
    historySaveIntervalTime OBJECT-TYPE
    SYNTAX INTEGER (0..65535)
    MAX-ACCESS read-write
    STATUS current
    DESCRIPTION 
        "The save interval time for history record data.
         The unit of actual value is minute."
    ::= { systemParameter 61 }
  -- 1.3.6.1.4.1.39553.10.3.4.62
    batteryCurveSaveTime OBJECT-TYPE
    SYNTAX INTEGER (0..65535)
    MAX-ACCESS read-write
    STATUS current
    DESCRIPTION 
        "The save interval time for battery curve record data.
         The unit of actual value is minute."
    ::= { systemParameter 62 }
  -- 1.3.6.1.4.1.39553.10.3.4.63
    screenLockTime OBJECT-TYPE
    SYNTAX INTEGER (0..1000)
    MAX-ACCESS read-write
    STATUS current
    DESCRIPTION 
        "The time for controller's LCD screen protection.
         The unit of actual value is minute."
    ::= { systemParameter 63 }
  -- 1.3.6.1.4.1.39553.10.3.4.64
    acVoltageVariationEnable OBJECT-TYPE
    SYNTAX INTEGER {
        disable (0),
        enable (1)
    }
    MAX-ACCESS read-write
    STATUS current
    DESCRIPTION 
        "The function for record history data when the AC input voltage change."
    ::= { systemParameter 64 }
  -- 1.3.6.1.4.1.39553.10.3.4.65
    acVoltageVariationRate OBJECT-TYPE
    SYNTAX INTEGER (5..20)
    MAX-ACCESS read-write
    STATUS current
    DESCRIPTION 
        "The function for record history data when the AC input voltage change value
         bigger than the setting value.
         The unit of actual value is %."
    ::= { systemParameter 65 }
  -- 1.3.6.1.4.1.39553.10.3.4.66
    dcVoltageVariationEnable OBJECT-TYPE
    SYNTAX INTEGER {
        disable (0),
        enable (1)
    }
    MAX-ACCESS read-write
    STATUS current
    DESCRIPTION 
        "The function for record history data when the bus output voltage change."
    ::= { systemParameter 66 }
  -- 1.3.6.1.4.1.39553.10.3.4.67
    dcVoltageVariationRate OBJECT-TYPE
    SYNTAX INTEGER (5..20)
    MAX-ACCESS read-write
    STATUS current
    DESCRIPTION 
        "The function for record history data when the bus output voltage change value
         bigger than the setting value.
         The unit of actual value is %."
    ::= { systemParameter 67 }
  -- 1.3.6.1.4.1.39553.10.3.4.68
    batteryCurrentVariationEnable OBJECT-TYPE
    SYNTAX INTEGER {
        disable (0),
        enable (1)
    }
    MAX-ACCESS read-write
    STATUS current
    DESCRIPTION 
        "The function for record history data when the battery current change."
    ::= { systemParameter 68 }
  -- 1.3.6.1.4.1.39553.10.3.4.69
    batteryCurrentVariationRate OBJECT-TYPE
    SYNTAX INTEGER (5..100)
    MAX-ACCESS read-write
    STATUS current
    DESCRIPTION 
        "The function for record history data when the battery current change value
         bigger than the setting value.
         The unit of actual value is %."
    ::= { systemParameter 69 }
  -- 1.3.6.1.4.1.39553.10.3.4.70
    loadCurrentVariationEnable OBJECT-TYPE
    SYNTAX INTEGER {
        disable (0),
        enable (1)
    }
    MAX-ACCESS read-write
    STATUS current
    DESCRIPTION 
        "The function for record history data when the load current change."
    ::= { systemParameter 70 }
  -- 1.3.6.1.4.1.39553.10.3.4.71
    loadCurrentVariationRate OBJECT-TYPE
    SYNTAX INTEGER (5..100)
    MAX-ACCESS read-write
    STATUS current
    DESCRIPTION 
        "The function for record history data when the load current change.
         The unit of actual value is %."
    ::= { systemParameter 71 }
  -- 1.3.6.1.4.1.39553.10.3.4.72
    variationSavePeriod OBJECT-TYPE
    SYNTAX INTEGER (5..300)
    MAX-ACCESS read-write
    STATUS current
    DESCRIPTION 
        "The function for record history data when the system signal change.
         The unit of actual value is second."
    ::= { systemParameter 72 }
  -- 1.3.6.1.4.1.39553.10.3.4.73
    snmpTrapSendTime OBJECT-TYPE
    SYNTAX INTEGER (0..6000)
    MAX-ACCESS read-write
    STATUS current
    DESCRIPTION 
        "The function for SNMP trap interval time.
         The unit of actual value is minute."
    ::= { systemParameter 73 }
  -- 1.3.6.1.4.1.39553.10.3.4.74
    snmpTrapAuthenticationSendTime OBJECT-TYPE
    SYNTAX INTEGER (0..6000)
    MAX-ACCESS read-write
    STATUS current
    DESCRIPTION 
        "The function for SNMP authentication trap interval time.
         The unit of actual value is minute."
    ::= { systemParameter 74 }
  -- 1.3.6.1.4.1.39553.10.3.4.75
    snmpTrapDestinationIPAddress1 OBJECT-TYPE
    SYNTAX IpAddress
    MAX-ACCESS read-write
    STATUS current
    DESCRIPTION 
        "The function for SNMP trap destination IP address 1."
    ::= { systemParameter 75 }
  -- 1.3.6.1.4.1.39553.10.3.4.76
    snmpTrapDestinationIPAddress2 OBJECT-TYPE
    SYNTAX IpAddress
    MAX-ACCESS read-write
    STATUS current
    DESCRIPTION 
        "The function for SNMP trap destination IP address 2."
    ::= { systemParameter 76 }
  -- 1.3.6.1.4.1.39553.10.3.4.77
    snmpTrapDestinationIPAddress3 OBJECT-TYPE
    SYNTAX IpAddress
    MAX-ACCESS read-write
    STATUS current
    DESCRIPTION 
        "The function for SNMP trap destination IP address 3."
    ::= { systemParameter 77 }
  -- 1.3.6.1.4.1.39553.10.3.4.78
    snmpTrapDestinationIPAddress4 OBJECT-TYPE
    SYNTAX IpAddress
    MAX-ACCESS read-write
    STATUS current
    DESCRIPTION 
        "The function for SNMP trap destination IP address 4."
    ::= { systemParameter 78 }
  -- 1.3.6.1.4.1.39553.10.3.4.79
    snmpTrapDestinationIPAddress5 OBJECT-TYPE
    SYNTAX IpAddress
    MAX-ACCESS read-write
    STATUS current
    DESCRIPTION 
        "The function for SNMP trap destination IP address 5."
    ::= { systemParameter 79 }
  -- 1.3.6.1.4.1.39553.10.3.4.80
    snmpTrapDestinationIPAddress6 OBJECT-TYPE
    SYNTAX IpAddress
    MAX-ACCESS read-write
    STATUS current
    DESCRIPTION 
        "The function for SNMP trap destination IP address 6."
    ::= { systemParameter 80 }
  -- 1.3.6.1.4.1.39553.10.3.4.81
    snmpTrapDestinationIPAddress7 OBJECT-TYPE
    SYNTAX IpAddress
    MAX-ACCESS read-write
    STATUS current
    DESCRIPTION 
        "The function for SNMP trap destination IP address 7."
    ::= { systemParameter 81 }
  -- 1.3.6.1.4.1.39553.10.3.4.82
    snmpTrapDestinationIPAddress8 OBJECT-TYPE
    SYNTAX IpAddress
    MAX-ACCESS read-write
    STATUS current
    DESCRIPTION 
        "The function for SNMP trap destination IP address 8."
    ::= { systemParameter 82 }
  -- 1.3.6.1.4.1.39553.10.3.4.83
    snmpTrapDestinationIPAddress9 OBJECT-TYPE
    SYNTAX IpAddress
    MAX-ACCESS read-write
    STATUS current
    DESCRIPTION 
        "The function for SNMP trap destination IP address 9."
    ::= { systemParameter 83 }
  -- 1.3.6.1.4.1.39553.10.3.4.84
    snmpTrapDestinationIPAddress10 OBJECT-TYPE
    SYNTAX IpAddress
    MAX-ACCESS read-write
    STATUS current
    DESCRIPTION 
        "The function for SNMP trap destination IP address 10."
    ::= { systemParameter 84 }
  -- 1.3.6.1.4.1.39553.10.3.4.85
    snmpTrapDestinationIPAddress11 OBJECT-TYPE
    SYNTAX IpAddress
    MAX-ACCESS read-write
    STATUS current
    DESCRIPTION 
        "The function for SNMP trap destination IP address 11."
    ::= { systemParameter 85 }
  -- 1.3.6.1.4.1.39553.10.3.4.86
    snmpTrapDestinationIPAddress12 OBJECT-TYPE
    SYNTAX IpAddress
    MAX-ACCESS read-write
    STATUS current
    DESCRIPTION 
        "The function for SNMP trap destination IP address 12."
    ::= { systemParameter 86 }
  -- 1.3.6.1.4.1.39553.10.3.4.87
    snmpTrapDestinationIPAddress13 OBJECT-TYPE
    SYNTAX IpAddress
    MAX-ACCESS read-write
    STATUS current
    DESCRIPTION 
        "The function for SNMP trap destination IP address 13."
    ::= { systemParameter 87 }
  -- 1.3.6.1.4.1.39553.10.3.4.88
    snmpTrapDestinationIPAddress14 OBJECT-TYPE
    SYNTAX IpAddress
    MAX-ACCESS read-write
    STATUS current
    DESCRIPTION 
        "The function for SNMP trap destination IP address 14."
    ::= { systemParameter 88 }
  -- 1.3.6.1.4.1.39553.10.3.4.89
    snmpTrapDestinationIPAddress15 OBJECT-TYPE
    SYNTAX IpAddress
    MAX-ACCESS read-write
    STATUS current
    DESCRIPTION 
        "The function for SNMP trap destination IP address 15."
    ::= { systemParameter 89 }
  -- 1.3.6.1.4.1.39553.10.3.4.90
    snmpTrapDestinationIPAddress16 OBJECT-TYPE
    SYNTAX IpAddress
    MAX-ACCESS read-write
    STATUS current
    DESCRIPTION 
        "The function for SNMP trap destination IP address 16."
    ::= { systemParameter 90 }
  -- 1.3.6.1.4.1.39553.10.3.4.91
    snmpTrapDestinationIPAddress17 OBJECT-TYPE
    SYNTAX IpAddress
    MAX-ACCESS read-write
    STATUS current
    DESCRIPTION 
        "The function for SNMP trap destination IP address 17."
    ::= { systemParameter 91 }
  -- 1.3.6.1.4.1.39553.10.3.4.92
    snmpTrapDestinationIPAddress18 OBJECT-TYPE
    SYNTAX IpAddress
    MAX-ACCESS read-write
    STATUS current
    DESCRIPTION 
        "The function for SNMP trap destination IP address 18."
    ::= { systemParameter 92 }
  -- 1.3.6.1.4.1.39553.10.3.4.93
    snmpTrapDestinationIPAddress19 OBJECT-TYPE
    SYNTAX IpAddress
    MAX-ACCESS read-write
    STATUS current
    DESCRIPTION 
        "The function for SNMP trap destination IP address 19."
    ::= { systemParameter 93 }
  -- 1.3.6.1.4.1.39553.10.3.4.94
    snmpTrapDestinationIPAddress20 OBJECT-TYPE
    SYNTAX IpAddress
    MAX-ACCESS read-write
    STATUS current
    DESCRIPTION 
        "The function for SNMP trap destination IP address 20."
    ::= { systemParameter 94 }
  -- 1.3.6.1.4.1.39553.10.3.4.95
    snmpTrapAuthDestinationIPAddress OBJECT-TYPE
    SYNTAX IpAddress
    MAX-ACCESS read-write
    STATUS current
    DESCRIPTION 
        "The function for SNMP trap authenticat destination IP address."
    ::= { systemParameter 95 }
  -- 1.3.6.1.4.1.39553.10.3.4.96
    snmpTrapUserName1 OBJECT-TYPE
    SYNTAX OCTET STRING (SIZE(0..28))
    MAX-ACCESS read-write
    STATUS current
    DESCRIPTION 
        "The function for SNMP trap destination 1 name."
    ::= { systemParameter 96 }
  -- 1.3.6.1.4.1.39553.10.3.4.97
    snmpTrapUserName2 OBJECT-TYPE
    SYNTAX OCTET STRING (SIZE(0..28))
    MAX-ACCESS read-write
    STATUS current
    DESCRIPTION 
        "The function for SNMP trap destination 2 name."
    ::= { systemParameter 97 }
  -- 1.3.6.1.4.1.39553.10.3.4.98
    snmpTrapUserName3 OBJECT-TYPE
    SYNTAX OCTET STRING (SIZE(0..28))
    MAX-ACCESS read-write
    STATUS current
    DESCRIPTION 
        "The function for SNMP trap destination 3 name."
    ::= { systemParameter 98 }
  -- 1.3.6.1.4.1.39553.10.3.4.99
    snmpTrapUserName4 OBJECT-TYPE
    SYNTAX OCTET STRING (SIZE(0..28))
    MAX-ACCESS read-write
    STATUS current
    DESCRIPTION 
        "The function for SNMP trap destination 4 name."
    ::= { systemParameter 99 }
  -- 1.3.6.1.4.1.39553.10.3.4.100
    snmpTrapUserName5 OBJECT-TYPE
    SYNTAX OCTET STRING (SIZE(0..28))
    MAX-ACCESS read-write
    STATUS current
    DESCRIPTION 
        "The function for SNMP trap destination 5 name."
    ::= { systemParameter 100 }
  -- 1.3.6.1.4.1.39553.10.3.4.101
    snmpTrapUserName6 OBJECT-TYPE
    SYNTAX OCTET STRING (SIZE(0..28))
    MAX-ACCESS read-write
    STATUS current
    DESCRIPTION 
        "The function for SNMP trap destination 6 name."
    ::= { systemParameter 101 }
  -- 1.3.6.1.4.1.39553.10.3.4.102
    snmpTrapUserName7 OBJECT-TYPE
    SYNTAX OCTET STRING (SIZE(0..28))
    MAX-ACCESS read-write
    STATUS current
    DESCRIPTION 
        "The function for SNMP trap destination 7 name."
    ::= { systemParameter 102 }
  -- 1.3.6.1.4.1.39553.10.3.4.103
    snmpTrapUserName8 OBJECT-TYPE
    SYNTAX OCTET STRING (SIZE(0..28))
    MAX-ACCESS read-write
    STATUS current
    DESCRIPTION 
        "The function for SNMP trap destination 8 name."
    ::= { systemParameter 103 }
  -- 1.3.6.1.4.1.39553.10.3.4.104
    snmpTrapUserName9 OBJECT-TYPE
    SYNTAX OCTET STRING (SIZE(0..28))
    MAX-ACCESS read-write
    STATUS current
    DESCRIPTION 
        "The function for SNMP trap destination 9 name."
    ::= { systemParameter 104 }
  -- 1.3.6.1.4.1.39553.10.3.4.105
    snmpTrapUserName10 OBJECT-TYPE
    SYNTAX OCTET STRING (SIZE(0..28))
    MAX-ACCESS read-write
    STATUS current
    DESCRIPTION 
        "The function for SNMP trap destination 10 name."
    ::= { systemParameter 105 }
  -- 1.3.6.1.4.1.39553.10.3.4.106
    snmpTrapUserName11 OBJECT-TYPE
    SYNTAX OCTET STRING (SIZE(0..28))
    MAX-ACCESS read-write
    STATUS current
    DESCRIPTION 
        "The function for SNMP trap destination 11 name."
    ::= { systemParameter 106 }
  -- 1.3.6.1.4.1.39553.10.3.4.107
    snmpTrapUserName12 OBJECT-TYPE
    SYNTAX OCTET STRING (SIZE(0..28))
    MAX-ACCESS read-write
    STATUS current
    DESCRIPTION 
        "The function for SNMP trap destination 12 name."
    ::= { systemParameter 107 }
  -- 1.3.6.1.4.1.39553.10.3.4.108
    snmpTrapUserName13 OBJECT-TYPE
    SYNTAX OCTET STRING (SIZE(0..28))
    MAX-ACCESS read-write
    STATUS current
    DESCRIPTION 
        "The function for SNMP trap destination 13 name."
    ::= { systemParameter 108 }
  -- 1.3.6.1.4.1.39553.10.3.4.109
    snmpTrapUserName14 OBJECT-TYPE
    SYNTAX OCTET STRING (SIZE(0..28))
    MAX-ACCESS read-write
    STATUS current
    DESCRIPTION 
        "The function for SNMP trap destination 14 name."
    ::= { systemParameter 109 }
  -- 1.3.6.1.4.1.39553.10.3.4.110
    snmpTrapUserName15 OBJECT-TYPE
    SYNTAX OCTET STRING (SIZE(0..28))
    MAX-ACCESS read-write
    STATUS current
    DESCRIPTION 
        "The function for SNMP trap destination 15 name."
    ::= { systemParameter 110 }
  -- 1.3.6.1.4.1.39553.10.3.4.111
    snmpTrapUserName16 OBJECT-TYPE
    SYNTAX OCTET STRING (SIZE(0..28))
    MAX-ACCESS read-write
    STATUS current
    DESCRIPTION 
        "The function for SNMP trap destination 16 name."
    ::= { systemParameter 111 }
  -- 1.3.6.1.4.1.39553.10.3.4.112
    snmpTrapUserName17 OBJECT-TYPE
    SYNTAX OCTET STRING (SIZE(0..28))
    MAX-ACCESS read-write
    STATUS current
    DESCRIPTION 
        "The function for SNMP trap destination 17 name."
    ::= { systemParameter 112 }
  -- 1.3.6.1.4.1.39553.10.3.4.113
    snmpTrapUserName18 OBJECT-TYPE
    SYNTAX OCTET STRING (SIZE(0..28))
    MAX-ACCESS read-write
    STATUS current
    DESCRIPTION 
        "The function for SNMP trap destination 18 name."
    ::= { systemParameter 113 }
  -- 1.3.6.1.4.1.39553.10.3.4.114
    snmpTrapUserName19 OBJECT-TYPE
    SYNTAX OCTET STRING (SIZE(0..28))
    MAX-ACCESS read-write
    STATUS current
    DESCRIPTION 
        "The function for SNMP trap destination 19 name."
    ::= { systemParameter 114 }
  -- 1.3.6.1.4.1.39553.10.3.4.115
    snmpTrapUserName20 OBJECT-TYPE
    SYNTAX OCTET STRING (SIZE(0..28))
    MAX-ACCESS read-write
    STATUS current
    DESCRIPTION 
        "The function for SNMP trap destination 20 name."
    ::= { systemParameter 115 }
  -- 1.3.6.1.4.1.39553.10.3.4.116
    snmpSetUserName OBJECT-TYPE
    SYNTAX OCTET STRING (SIZE(0..28))
    MAX-ACCESS read-write
    STATUS current
    DESCRIPTION 
        "The function for SNMP SET function name."
    ::= { systemParameter 116 }
  -- 1.3.6.1.4.1.39553.10.3.4.117
    snmpGetUserName OBJECT-TYPE
    SYNTAX OCTET STRING (SIZE(0..28))
    MAX-ACCESS read-write
    STATUS current
    DESCRIPTION 
        "The function for SNMP GET function name."
    ::= { systemParameter 117 }
  -- 1.3.6.1.4.1.39553.10.3.4.118
    systemType OBJECT-TYPE
    SYNTAX INTEGER {
        typeI(0),
        typeII(1),
        typeIII(2),
        typeIV(3)
    }
    MAX-ACCESS read-write
    STATUS current
    DESCRIPTION 
        "The system type for alarm and LVD function."
    ::= { systemParameter 118 }
    -- 1.3.6.1.4.1.39553.10.3.4.119
    solarSlotEnable OBJECT-TYPE
    SYNTAX INTEGER {
        disable(0),
        enable(1)
    }
    MAX-ACCESS read-write
    STATUS current
    DESCRIPTION 
        "Enable solar slot function."
    ::= { systemParameter 119 }
  -- 1.3.6.1.4.1.39553.10.3.4.121
    screenDirection OBJECT-TYPE
    SYNTAX INTEGER {
        horizontal (0),
        vertical (1)
    }
    MAX-ACCESS read-write
    STATUS current
    DESCRIPTION 
        "The controller's LCD display direction."
    ::= { systemParameter 121 }
  -- 1.3.6.1.4.1.39553.10.3.4.122
    alarmBlock OBJECT-TYPE
    SYNTAX INTEGER {
        notblock (0),
        block (1)
    }
    MAX-ACCESS read-write
    STATUS current
    DESCRIPTION 
        "The alarm block function for serial communication."
    ::= { systemParameter 122 }
  -- 1.3.6.1.4.1.39553.10.3.4.123
    pueCalculate OBJECT-TYPE
    SYNTAX INTEGER {
        disable (0),
        enable (1)
    }
    MAX-ACCESS read-write
    STATUS current
    DESCRIPTION 
        "The enable for PUE calculate function."
    ::= { systemParameter 123 }
  -- 1.3.6.1.4.1.39553.10.3.4.124
    slotEnableRectifier OBJECT-TYPE
    SYNTAX INTEGER {
        disable (0),
        enable (1)
    }
    MAX-ACCESS read-write
    STATUS current
    DESCRIPTION 
        "The enable for slot setting function for rectifier."
    ::= { systemParameter 124 }
  -- 1.3.6.1.4.1.39553.10.3.4.125
    snmTrapEnable OBJECT-TYPE
    SYNTAX INTEGER {
        disable (0),
        enable (1)
    }
    MAX-ACCESS read-write
    STATUS current
    DESCRIPTION 
        "The enable for SNMP TRAP function."
    ::= { systemParameter 125 }
  -- 1.3.6.1.4.1.39553.10.3.4.126
    acVoltageDisplayMode OBJECT-TYPE
    SYNTAX INTEGER {
        lineVoltage (0),
        phaseVoltage (1)
    }
    MAX-ACCESS read-write
    STATUS current
    DESCRIPTION 
        "The AC input voltage display mode.
         0 = display line voltage,
         1 = display phase voltage."
    ::= { systemParameter 126 }
  -- 1.3.6.1.4.1.39553.10.3.4.127
    acSampleEnable OBJECT-TYPE
    SYNTAX INTEGER {
        disable (0),
        enable (1)
    }
    MAX-ACCESS read-write
    STATUS current
    DESCRIPTION 
        "The enable for AC sample function."
    ::= { systemParameter 127 }
  -- 1.3.6.1.4.1.39553.10.3.4.128
    dcCabientMasterSlave OBJECT-TYPE
    SYNTAX INTEGER {
        master (0),
        slave (1)
    }
    MAX-ACCESS read-write
    STATUS current
    DESCRIPTION 
        "The selection for the DC cabinet attribute which is master or slave."
    ::= { systemParameter 128 }
  -- 1.3.6.1.4.1.39553.10.3.4.129
    efficiencyDisplayEnable OBJECT-TYPE
    SYNTAX INTEGER {
        notDisplay (0),
        display (1)
    }
    MAX-ACCESS read-write
    STATUS current
    DESCRIPTION 
        "The system efficiency display or not-display."
    ::= { systemParameter 129 }
  -- 1.3.6.1.4.1.39553.10.3.4.130
    pueDisplayEnable OBJECT-TYPE
    SYNTAX INTEGER {
        notdisplay (0),
        display (1)
    }
    MAX-ACCESS read-write
    STATUS current
    DESCRIPTION 
        "The system PUE display or not-display."
    ::= { systemParameter 130 }
  -- 1.3.6.1.4.1.39553.10.3.4.131
    loadRateDisplayEnable OBJECT-TYPE
    SYNTAX INTEGER {
        notdisplay (0),
        display (1)
    }
    MAX-ACCESS read-write
    STATUS current
    DESCRIPTION 
        "The system load rate display or not-display."
    ::= { systemParameter 131 }
  -- 1.3.6.1.4.1.39553.10.3.4.132
    currentTHDDisplayEnable OBJECT-TYPE
    SYNTAX INTEGER {
        notdisplay (0),
        display (1)
    }
    MAX-ACCESS read-write
    STATUS current
    DESCRIPTION 
        "The AC current THD display or not-display."
    ::= { systemParameter 132 }
  -- 1.3.6.1.4.1.39553.10.3.4.133
    voltageTHDDisplayEnable OBJECT-TYPE
    SYNTAX INTEGER {
        notdisplay (0),
        display (1)
    }
    MAX-ACCESS read-write
    STATUS current
    DESCRIPTION 
        "The AC voltage THD display or not-display."
    ::= { systemParameter 133 }
  -- 1.3.6.1.4.1.39553.10.3.4.134
    acOnworkDisplayEnable OBJECT-TYPE
    SYNTAX INTEGER {
        notdisplay (0),
        display (1)
    }
    MAX-ACCESS read-write
    STATUS current
    DESCRIPTION 
        "The AC on work display or not-display."
    ::= { systemParameter 134 }
  -- 1.3.6.1.4.1.39553.10.3.4.135
    energyDisplayEnable OBJECT-TYPE
    SYNTAX INTEGER {
        notdisplay (0),
        display (1)
    }
    MAX-ACCESS read-write
    STATUS current
    DESCRIPTION 
        "The energy display or not-display."
    ::= { systemParameter 135 }
  -- 1.3.6.1.4.1.39553.10.3.4.136
    acInputMode OBJECT-TYPE
    SYNTAX INTEGER {
        mainsInput (0),
        mainsAndDGInput (1),
        dgInput (2),
        twoDGInput (3)
    }
    MAX-ACCESS read-write
    STATUS current
    DESCRIPTION 
        "The selection mode for the AC input."
    ::= { systemParameter 136 }
  -- 1.3.6.1.4.1.39553.10.3.4.137
    newEnergyMode OBJECT-TYPE
    SYNTAX INTEGER {
        none (0),
        soalr (1),
        wind (2),
        windAndSolar (3)
    }
    MAX-ACCESS read-write
    STATUS current
    DESCRIPTION 
        "The selection for the new energy mode."
    ::= { systemParameter 137 }
  -- 1.3.6.1.4.1.39553.10.3.4.138
    acPhaseNumber OBJECT-TYPE
    SYNTAX INTEGER {
        threePhase (0),
        singlePhase (1)
    }
    MAX-ACCESS read-write
    STATUS current
    DESCRIPTION 
        "The AC input number."
    ::= { systemParameter 138 }
    -- 1.3.6.1.4.1.39553.10.3.4.139
    alarmSoundBlock OBJECT-TYPE
    SYNTAX INTEGER {
        notblock (0),
        block (1)
    }
    MAX-ACCESS read-write
    STATUS current
    DESCRIPTION 
        "The buzzer sound for the alarm occured."
    ::= { systemParameter 139 }
    -- 1.3.6.1.4.1.39553.10.3.4.140
    snmpTrapVersion OBJECT-TYPE
    SYNTAX INTEGER {
        v1 (0),
        v2 (1)
    }
    MAX-ACCESS read-write
    STATUS current
    DESCRIPTION 
        "The SNMP TRAP version."
    ::= { systemParameter 140 }
    -- 1.3.6.1.4.1.39553.10.3.4.141
    altitude OBJECT-TYPE
    SYNTAX INTEGER (-1000000..3000000)
    MAX-ACCESS read-write
    STATUS current
    DESCRIPTION 
        "The system's altitude.
         The actual value = The set or receive data / 100.
         The unit of actual value is meter(m)."
    ::= { systemParameter 141 }
    -- 1.3.6.1.4.1.39553.10.3.4.142
    rectifierOVSDEnable OBJECT-TYPE
    SYNTAX INTEGER {
        disable (0),
        enable (1)
    }
    MAX-ACCESS read-write
    STATUS current
    DESCRIPTION 
        "The enable for the rectifier OVSD function."
    ::= { systemParameter 142 }
    -- 1.3.6.1.4.1.39553.10.3.4.143
    acdcRectifierNumber OBJECT-TYPE
    SYNTAX INTEGER (0..128)
    MAX-ACCESS read-write
    STATUS current
    DESCRIPTION 
        "The number of the ACDC-Rectifier."
    ::= { systemParameter 143 }
    -- 1.3.6.1.4.1.39553.10.3.4.144
    solarModuleNumber OBJECT-TYPE
    SYNTAX INTEGER (0..20)
    MAX-ACCESS read-write
    STATUS current
    DESCRIPTION 
        "The number of the solar-Controller."
    ::= { systemParameter 144 }
    -- 1.3.6.1.4.1.39553.10.3.4.145
    windModuleNumber OBJECT-TYPE
    SYNTAX INTEGER (0..20)
    MAX-ACCESS read-write
    STATUS current
    DESCRIPTION 
        "The number of the wind-Moudle."
    ::= { systemParameter 145 }
    -- 1.3.6.1.4.1.39553.10.3.4.146
    inverterModuleNumber OBJECT-TYPE
    SYNTAX INTEGER (0..20)
    MAX-ACCESS read-write
    STATUS current
    DESCRIPTION 
        "The number of the inverter-Moudle."
    ::= { systemParameter 146 }
    -- 1.3.6.1.4.1.39553.10.3.4.147
    dcdcRectifierNumber OBJECT-TYPE
    SYNTAX INTEGER (0..20)
    MAX-ACCESS read-write
    STATUS current
    DESCRIPTION 
        "The number of the DCDC-Rectifier."
    ::= { systemParameter 147 }
    -- 1.3.6.1.4.1.39553.10.3.4.148
    tcpModbusPort OBJECT-TYPE
    SYNTAX INTEGER (0..65535)
    MAX-ACCESS read-write
    STATUS current
    DESCRIPTION 
        "The port of the TCP MODBUS."
    ::= { systemParameter 148 }
    -- 1.3.6.1.4.1.39553.10.3.4.149
    ntpServerIPAddress OBJECT-TYPE
    SYNTAX IpAddress
    MAX-ACCESS read-write
    STATUS current
    DESCRIPTION 
        "The IP address of NTP server."
    ::= { systemParameter 149 }
    -- 1.3.6.1.4.1.39553.10.3.4.150
    ntpIntervalTime OBJECT-TYPE
    SYNTAX INTEGER (0..44640)
    MAX-ACCESS read-write
    STATUS current
    DESCRIPTION 
        "The interval time of NTP.
        The unit is minute"
    ::= { systemParameter 150 }
    -- 1.3.6.1.4.1.39553.10.3.4.151
    senderEmailAddress OBJECT-TYPE
    SYNTAX OCTET STRING (SIZE(0..50))
    MAX-ACCESS read-write
    STATUS current
    DESCRIPTION 
        "The email address of sender."
    ::= { systemParameter 151 }
    -- 1.3.6.1.4.1.39553.10.3.4.152
    senderEmailPassword OBJECT-TYPE
    SYNTAX OCTET STRING (SIZE(0..20))
    MAX-ACCESS read-write
    STATUS current
    DESCRIPTION 
        "The email password of sender."
    ::= { systemParameter 152 }
    -- 1.3.6.1.4.1.39553.10.3.4.153
    recipientEmailAddress1 OBJECT-TYPE
    SYNTAX OCTET STRING (SIZE(0..50))
    MAX-ACCESS read-write
    STATUS current
    DESCRIPTION 
        "The email address 1 of recipient."
    ::= { systemParameter 153 }
    -- 1.3.6.1.4.1.39553.10.3.4.154
    recipientEmailAddress2 OBJECT-TYPE
    SYNTAX OCTET STRING (SIZE(0..50))
    MAX-ACCESS read-write
    STATUS current
    DESCRIPTION 
        "The email address 2 of recipient."
    ::= { systemParameter 154 }
    -- 1.3.6.1.4.1.39553.10.3.4.155
    recipientEmailAddress3 OBJECT-TYPE
    SYNTAX OCTET STRING (SIZE(0..50))
    MAX-ACCESS read-write
    STATUS current
    DESCRIPTION 
        "The email address 3 of recipient."
    ::= { systemParameter 155 }
    -- 1.3.6.1.4.1.39553.10.3.4.156
    recipientEmailAddress4 OBJECT-TYPE
    SYNTAX OCTET STRING (SIZE(0..50))
    MAX-ACCESS read-write
    STATUS current
    DESCRIPTION 
        "The email address 4 of recipient."
    ::= { systemParameter 156 }
    -- 1.3.6.1.4.1.39553.10.3.4.157
    recipientEmailAddress5 OBJECT-TYPE
    SYNTAX OCTET STRING (SIZE(0..50))
    MAX-ACCESS read-write
    STATUS current
    DESCRIPTION 
        "The email address 5 of recipient."
    ::= { systemParameter 157 }
    -- 1.3.6.1.4.1.39553.10.3.4.158
    senderEmailServerIPAddress OBJECT-TYPE
    SYNTAX IpAddress
    MAX-ACCESS read-write
    STATUS current
    DESCRIPTION 
        "The server IP address of email sender."
    ::= { systemParameter 158 }
    -- 1.3.6.1.4.1.39553.10.3.4.159
    senderEmailServerPort OBJECT-TYPE
    SYNTAX INTEGER (0..65535)
    MAX-ACCESS read-write
    STATUS current
    DESCRIPTION 
        "The server port of email sender."
    ::= { systemParameter 159 }
    -- 1.3.6.1.4.1.39553.10.3.4.160
    sendEmailEnable OBJECT-TYPE
    SYNTAX INTEGER {
        disable (0),
        minorAlarm (1),
        majorAlarm (2),
        criticalAlarm (3),
        minorAlarmMajorAlarm (4),
        minorAlarmCriticalAlarm (5),
        majorAlarmCriticalAlarm (6),
        allAlarm (7)
    }
    MAX-ACCESS read-write
    STATUS current
    DESCRIPTION 
        "The enable for sending email when alarm happen."
    ::= { systemParameter 160 }
    -- 1.3.6.1.4.1.39553.10.3.4.161
    dhcpEnable OBJECT-TYPE
    SYNTAX INTEGER {
        disable (0),
        enable (1)
    }
    MAX-ACCESS read-write
    STATUS current
    DESCRIPTION 
        "The enable for DHCP."
    ::= { systemParameter 161 }
    -- 1.3.6.1.4.1.39553.10.3.4.162
    snmpAgentPort OBJECT-TYPE
    SYNTAX INTEGER (0..65535)
    MAX-ACCESS read-write
    STATUS current
    DESCRIPTION 
        "The port of snmp agent."
    ::= { systemParameter 162 }
    -- 1.3.6.1.4.1.39553.10.3.4.163
    snmpTrapPort OBJECT-TYPE
    SYNTAX INTEGER (0..65535)
    MAX-ACCESS read-write
    STATUS current
    DESCRIPTION 
        "The port of snmp trap."
    ::= { systemParameter 163 }
    -- 1.3.6.1.4.1.39553.10.3.4.164
    siteName OBJECT-TYPE
    SYNTAX OCTET STRING (SIZE(0..30))
    MAX-ACCESS read-write
    STATUS current
    DESCRIPTION 
        "The name of Site."
    ::= { systemParameter 164 }
    -- 1.3.6.1.4.1.39553.10.3.4.165
    bmmNumber OBJECT-TYPE
    SYNTAX INTEGER (0..10)
    MAX-ACCESS read-write
    STATUS current
    DESCRIPTION 
        "The number of BMM."
    ::= { systemParameter 165 }
    -- 1.3.6.1.4.1.39553.10.3.4.166
    cellsNumber OBJECT-TYPE
    SYNTAX INTEGER (0..240)
    MAX-ACCESS read-write
    STATUS current
    DESCRIPTION 
        "The number of battery cells."
    ::= { systemParameter 166 }
    -- 1.3.6.1.4.1.39553.10.3.4.167
    siteID OBJECT-TYPE
    SYNTAX DisplayString (SIZE(0..30))
    MAX-ACCESS read-write
    STATUS current
    DESCRIPTION 
        "The ID of site."
    ::= { systemParameter 167 }
    -- 1.3.6.1.4.1.39553.10.3.4.168
    siteAddress OBJECT-TYPE
    SYNTAX DisplayString (SIZE(0..50))
    MAX-ACCESS read-write
    STATUS current
    DESCRIPTION 
        "The address of site."
    ::= { systemParameter 168 }
    -- 1.3.6.1.4.1.39553.10.3.4.169
    saveModuleInfoInIntervalTime OBJECT-TYPE
    SYNTAX INTEGER {
        disable (0),
        enable (1)
    }
    MAX-ACCESS read-write
    STATUS current
    DESCRIPTION 
        "Save Module Information In Interval Time."
    ::= { systemParameter 169 }
    -- 1.3.6.1.4.1.39553.10.3.4.170
    saveRunInfoWhenSystemAlarm OBJECT-TYPE
    SYNTAX INTEGER {
        disable (0),
        enable (1)
    }
    MAX-ACCESS read-write
    STATUS current
    DESCRIPTION 
        "Save Run Information When System Alarm."
    ::= { systemParameter 170 }
    
--------------------------------------------------------------------------
--  DC Distribution Battery Management Parameter{ dpcDistributedPower 5 }
--------------------------------------------------------------------------
-- 1.3.6.1.4.1.39553.10.3.5
    batteryManagementParameter OBJECT IDENTIFIER ::= { dcDistribution 5 }   

  -- 1.3.6.1.4.1.39553.10.3.5.1
    batteryShuntNumber OBJECT-TYPE
    SYNTAX INTEGER(0..8)
    MAX-ACCESS read-write
    STATUS current
    DESCRIPTION
    "The number of battery shunt in system.
     Default number:1."
    ::= { batteryManagementParameter 1 }
  -- 1.3.6.1.4.1.39553.10.3.5.2
    batteryType OBJECT-TYPE
    SYNTAX INTEGER {
        vrla (0),
        lfp (1)
    }
    MAX-ACCESS read-write
    STATUS current
    DESCRIPTION
    "The type of battery in system.
     Default type:VRLA (0)."
    ::= { batteryManagementParameter 2 }
  -- 1.3.6.1.4.1.39553.10.3.5.3
    batteryTimingTest1EnableOption OBJECT-TYPE
    SYNTAX INTEGER {
        disable (0),
        enable (1)
    }
    MAX-ACCESS read-write
    STATUS current
    DESCRIPTION
    "The enable option for battery timing test 1 function."
    ::= { batteryManagementParameter 3 }
  -- 1.3.6.1.4.1.39553.10.3.5.4
    batteryTimingTest2EnableOption OBJECT-TYPE
    SYNTAX INTEGER {
        disable (0),
        enable (1)
    }
    MAX-ACCESS read-write
    STATUS current
    DESCRIPTION
    "The enable option for battery timing test 2 function."
    ::= { batteryManagementParameter 4 }
  -- 1.3.6.1.4.1.39553.10.3.5.5
    batteryTimingTest3EnableOption OBJECT-TYPE
    SYNTAX INTEGER {
        disable (0),
        enable (1)
    }
    MAX-ACCESS read-write
    STATUS current
    DESCRIPTION
    "The enable option for battery timing test 3 function."
    ::= { batteryManagementParameter 5 }
  -- 1.3.6.1.4.1.39553.10.3.5.6
    batteryTimingTest4EnableOption OBJECT-TYPE
    SYNTAX INTEGER {
        disable (0),
        enable (1)
    }
    MAX-ACCESS read-write
    STATUS current
    DESCRIPTION
    "The enable option for battery timing test 4 function."
    ::= { batteryManagementParameter 6 }
  -- 1.3.6.1.4.1.39553.10.3.5.7
    batteryTimingTest1Year OBJECT-TYPE
    SYNTAX INTEGER
    MAX-ACCESS read-write
    STATUS current
    DESCRIPTION
    "The time of Year in battery timing test 1.
     The actual value = the receive data."
    ::= { batteryManagementParameter 7 }
  -- 1.3.6.1.4.1.39553.10.3.5.8
    batteryTimingTest2Year OBJECT-TYPE
    SYNTAX INTEGER
    MAX-ACCESS read-write
    STATUS current
    DESCRIPTION
    "The time of Year in battery timing test 2.
     The actual value = the receive data."
    ::= { batteryManagementParameter 8 }
  -- 1.3.6.1.4.1.39553.10.3.5.9
    batteryTimingTest3Year OBJECT-TYPE
    SYNTAX INTEGER
    MAX-ACCESS read-write
    STATUS current
    DESCRIPTION
    "The time of Year in battery timing test 3.
     The actual value = the receive data."
    ::= { batteryManagementParameter 9 }
  -- 1.3.6.1.4.1.39553.10.3.5.10
    batteryTimingTest4Year OBJECT-TYPE
    SYNTAX INTEGER
    MAX-ACCESS read-write
    STATUS current
    DESCRIPTION
    "The time of Year in battery timing test 4.
     The actual value = the receive data."
    ::= { batteryManagementParameter 10 }
  -- 1.3.6.1.4.1.39553.10.3.5.11
    batteryTimingTest1Month OBJECT-TYPE
    SYNTAX INTEGER
    MAX-ACCESS read-write
    STATUS current
    DESCRIPTION
    "The time of month in battery timing test 1.
     The actual value = the receive data."
    ::= { batteryManagementParameter 11 }
  -- 1.3.6.1.4.1.39553.10.3.5.12
    batteryTimingTest2Month OBJECT-TYPE
    SYNTAX INTEGER
    MAX-ACCESS read-write
    STATUS current
    DESCRIPTION
    "The time of month in battery timing test 2.
     The actual value = the receive data."
    ::= { batteryManagementParameter 12 }
  -- 1.3.6.1.4.1.39553.10.3.5.13
    batteryTimingTest3Month OBJECT-TYPE
    SYNTAX INTEGER
    MAX-ACCESS read-write
    STATUS current
    DESCRIPTION
    "The time of month in battery timing test 3.
     The actual value = the receive data."
    ::= { batteryManagementParameter 13 }
  -- 1.3.6.1.4.1.39553.10.3.5.14
    batteryTimingTest4Month OBJECT-TYPE
    SYNTAX INTEGER
    MAX-ACCESS read-write
    STATUS current
    DESCRIPTION
    "The time of month in battery timing test 4.
     The actual value = the receive data."
    ::= { batteryManagementParameter 14 }
  -- 1.3.6.1.4.1.39553.10.3.5.15
    batteryTimingTest1Day OBJECT-TYPE
    SYNTAX INTEGER
    MAX-ACCESS read-write
    STATUS current
    DESCRIPTION
    "The time of day in battery timing test 1.
     The actual value = the receive data."
    ::= { batteryManagementParameter 15 }
  -- 1.3.6.1.4.1.39553.10.3.5.16
    batteryTimingTest2Day OBJECT-TYPE
    SYNTAX INTEGER
    MAX-ACCESS read-write
    STATUS current
    DESCRIPTION
    "The time of day in battery timing test 2.
     The actual value = the receive data."
    ::= { batteryManagementParameter 16 }
  -- 1.3.6.1.4.1.39553.10.3.5.17
    batteryTimingTest3Day OBJECT-TYPE
    SYNTAX INTEGER
    MAX-ACCESS read-write
    STATUS current
    DESCRIPTION
    "The time of day in battery timing test 3.
     The actual value = the receive data."
    ::= { batteryManagementParameter 17 }
  -- 1.3.6.1.4.1.39553.10.3.5.18
    batteryTimingTest4Day OBJECT-TYPE
    SYNTAX INTEGER
    MAX-ACCESS read-write
    STATUS current
    DESCRIPTION
    "The time of day in battery timing test 4.
     The actual value = the receive data."
    ::= { batteryManagementParameter 18 }
  -- 1.3.6.1.4.1.39553.10.3.5.19
    batteryTimingTest1Hour OBJECT-TYPE
    SYNTAX INTEGER
    MAX-ACCESS read-write
    STATUS current
    DESCRIPTION
    "The time of hour in battery timing test 1.
     The actual value = the receive data."
    ::= { batteryManagementParameter 19 }
  -- 1.3.6.1.4.1.39553.10.3.5.20
    batteryTimingTest2Hour OBJECT-TYPE
    SYNTAX INTEGER
    MAX-ACCESS read-write
    STATUS current
    DESCRIPTION
    "The time of hour in battery timing test 2.
     The actual value = the receive data."
    ::= { batteryManagementParameter 20 }
  -- 1.3.6.1.4.1.39553.10.3.5.21
    batteryTimingTest3Hour OBJECT-TYPE
    SYNTAX INTEGER
    MAX-ACCESS read-write
    STATUS current
    DESCRIPTION
    "The time of hour in battery timing test 3.
     The actual value = the receive data."
    ::= { batteryManagementParameter 21 }
  -- 1.3.6.1.4.1.39553.10.3.5.22
    batteryTimingTest4Hour OBJECT-TYPE
    SYNTAX INTEGER
    MAX-ACCESS read-write
    STATUS current
    DESCRIPTION
    "The time of hour in battery timing test 4.
     The actual value = the receive data."
    ::= { batteryManagementParameter 22 }
  -- 1.3.6.1.4.1.39553.10.3.5.23
    batteryTimingTest1Minute OBJECT-TYPE
    SYNTAX INTEGER
    MAX-ACCESS read-write
    STATUS current
    DESCRIPTION
    "The time of minute in battery timing test 1.
     The actual value = the receive data."
    ::= { batteryManagementParameter 23 }
  -- 1.3.6.1.4.1.39553.10.3.5.24
    batteryTimingTest2Minute OBJECT-TYPE
    SYNTAX INTEGER
    MAX-ACCESS read-write
    STATUS current
    DESCRIPTION
    "The time of minute in battery timing test 2.
     The actual value = the receive data."
    ::= { batteryManagementParameter 24 }
  -- 1.3.6.1.4.1.39553.10.3.5.25
    batteryTimingTest3Minute OBJECT-TYPE
    SYNTAX INTEGER
    MAX-ACCESS read-write
    STATUS current
    DESCRIPTION
    "The time of minute in battery timing test 3.
     The actual value = the receive data."
    ::= { batteryManagementParameter 25 }
  -- 1.3.6.1.4.1.39553.10.3.5.26
    batteryTimingTest4Minute OBJECT-TYPE
    SYNTAX INTEGER
    MAX-ACCESS read-write
    STATUS current
    DESCRIPTION
    "The time of minute in battery timing test 4.
     The actual value = the receive data."
    ::= { batteryManagementParameter 26 }
  -- 1.3.6.1.4.1.39553.10.3.5.27
    llvd1EnableOption OBJECT-TYPE
    SYNTAX INTEGER {
        none (0),
        disable (1),
        enable (2)
    }
    MAX-ACCESS read-write
    STATUS current
    DESCRIPTION
    "The enable option for LLVD 1 function."
    ::= { batteryManagementParameter 27 }
  -- 1.3.6.1.4.1.39553.10.3.5.28
    llvd2EnableOption OBJECT-TYPE
    SYNTAX INTEGER {
        none (0),
        disable (1),
        enable (2)
    }
    MAX-ACCESS read-write
    STATUS current
    DESCRIPTION
    "The enable option for LLVD 2 function."
    ::= { batteryManagementParameter 28 }
  -- 1.3.6.1.4.1.39553.10.3.5.29
    llvd3EnableOption OBJECT-TYPE
    SYNTAX INTEGER {
        none (0),
        disable (1),
        enable (2)
    }
    MAX-ACCESS read-write
    STATUS current
    DESCRIPTION
    "The enable option for LLVD 3 function."
    ::= { batteryManagementParameter 29 }
  -- 1.3.6.1.4.1.39553.10.3.5.30
    llvd4EnableOption OBJECT-TYPE
    SYNTAX INTEGER {
        none (0),
        disable (1),
        enable (2)
    }
    MAX-ACCESS read-write
    STATUS current
    DESCRIPTION
    "The enable option for LLVD 4 function."
    ::= { batteryManagementParameter 30 }
  -- 1.3.6.1.4.1.39553.10.3.5.31
    llvd5EnableOption OBJECT-TYPE
    SYNTAX INTEGER {
        none (0),
        disable (1),
        enable (2)
    }
    MAX-ACCESS read-write
    STATUS current
    DESCRIPTION
    "The enable option for LLVD 5 function."
    ::= { batteryManagementParameter 31 }
  -- 1.3.6.1.4.1.39553.10.3.5.32
    llvd6EnableOption OBJECT-TYPE
    SYNTAX INTEGER {
        none (0),
        disable (1),
        enable (2)
    }
    MAX-ACCESS read-write
    STATUS current
    DESCRIPTION
    "The enable option for LLVD 6 function."
    ::= { batteryManagementParameter 32 }
  -- 1.3.6.1.4.1.39553.10.3.5.33
    llvd7EnableOption OBJECT-TYPE
    SYNTAX INTEGER {
        none (0),
        disable (1),
        enable (2)
    }
    MAX-ACCESS read-write
    STATUS current
    DESCRIPTION
    "The enable option for LLVD 7 function."
    ::= { batteryManagementParameter 33 }
  -- 1.3.6.1.4.1.39553.10.3.5.34
    llvd8EnableOption OBJECT-TYPE
    SYNTAX INTEGER {
        none (0),
        disable (1),
        enable (2)
    }
    MAX-ACCESS read-write
    STATUS current
    DESCRIPTION
    "The enable option for LLVD 8 function."
    ::= { batteryManagementParameter 34 }
  -- 1.3.6.1.4.1.39553.10.3.5.35
    llvd1Name OBJECT-TYPE
    SYNTAX OCTET STRING
    MAX-ACCESS read-write
    STATUS current
    DESCRIPTION
    "The name of LLVD 1.
     The length of character string is 10."
    ::= { batteryManagementParameter 35 }
  -- 1.3.6.1.4.1.39553.10.3.5.36
    llvd2Name OBJECT-TYPE
    SYNTAX OCTET STRING
    MAX-ACCESS read-write
    STATUS current
    DESCRIPTION
    "The name of LLVD 2.
     The length of character string is 10."
    ::= { batteryManagementParameter 36 }
  -- 1.3.6.1.4.1.39553.10.3.5.37
    llvd3Name OBJECT-TYPE
    SYNTAX OCTET STRING
    MAX-ACCESS read-write
    STATUS current
    DESCRIPTION
    "The name of LLVD 3.
     The length of character string is 10."
    ::= { batteryManagementParameter 37 }
  -- 1.3.6.1.4.1.39553.10.3.5.38
    llvd4Name OBJECT-TYPE
    SYNTAX OCTET STRING
    MAX-ACCESS read-write
    STATUS current
    DESCRIPTION
    "The name of LLVD 4.
     The length of character string is 10."
    ::= { batteryManagementParameter 38 }
  -- 1.3.6.1.4.1.39553.10.3.5.39
    llvd5Name OBJECT-TYPE
    SYNTAX OCTET STRING
    MAX-ACCESS read-write
    STATUS current
    DESCRIPTION
    "The name of LLVD 5.
     The length of character string is 10."
    ::= { batteryManagementParameter 39 }
  -- 1.3.6.1.4.1.39553.10.3.5.40
    llvd6Name OBJECT-TYPE
    SYNTAX OCTET STRING
    MAX-ACCESS read-write
    STATUS current
    DESCRIPTION
    "The name of LLVD 5.
     The length of character string is 10."
    ::= { batteryManagementParameter 40 }
  -- 1.3.6.1.4.1.39553.10.3.5.41
    llvd7Name OBJECT-TYPE
    SYNTAX OCTET STRING
    MAX-ACCESS read-write
    STATUS current
    DESCRIPTION
    "The name of LLVD 7.
     The length of character string is 10."
    ::= { batteryManagementParameter 41 }
  -- 1.3.6.1.4.1.39553.10.3.5.42
    llvd8Name OBJECT-TYPE
    SYNTAX OCTET STRING
    MAX-ACCESS read-write
    STATUS current
    DESCRIPTION
    "The name of LLVD 8.
     The length of character string is 10."
    ::= { batteryManagementParameter 42 }
  -- 1.3.6.1.4.1.39553.10.3.5.43
    llvd1contactorType OBJECT-TYPE
    SYNTAX INTEGER {
        biStable (0),
        no (1),
        nc (2)
    }
    MAX-ACCESS read-write
    STATUS current
    DESCRIPTION
    "The type of contactor for LLVD 1."
    ::= { batteryManagementParameter 43 }
  -- 1.3.6.1.4.1.39553.10.3.5.44
    llvd2contactorType OBJECT-TYPE
    SYNTAX INTEGER {
        biStable (0),
        no (1),
        nc (2)
    }
    MAX-ACCESS read-write
    STATUS current
    DESCRIPTION
    "The type of contactor for LLVD 2."
    ::= { batteryManagementParameter 44 }
  -- 1.3.6.1.4.1.39553.10.3.5.45
    llvd3contactorType OBJECT-TYPE
    SYNTAX INTEGER {
        biStable (0),
        no (1),
        nc (2)
    }
    MAX-ACCESS read-write
    STATUS current
    DESCRIPTION
    "The type of contactor for LLVD 3."
    ::= { batteryManagementParameter 45 }
  -- 1.3.6.1.4.1.39553.10.3.5.46
    llvd4contactorType OBJECT-TYPE
    SYNTAX INTEGER {
        biStable (0),
        no (1),
        nc (2)
    }
    MAX-ACCESS read-write
    STATUS current
    DESCRIPTION
    "The type of contactor for LLVD 4."
    ::= { batteryManagementParameter 46 }
  -- 1.3.6.1.4.1.39553.10.3.5.47
    llvd5contactorType OBJECT-TYPE
    SYNTAX INTEGER {
        biStable (0),
        no (1),
        nc (2)
    }
    MAX-ACCESS read-write
    STATUS current
    DESCRIPTION
    "The type of contactor for LLVD 5."
    ::= { batteryManagementParameter 47 }
  -- 1.3.6.1.4.1.39553.10.3.5.48
    llvd6contactorType OBJECT-TYPE
    SYNTAX INTEGER {
        biStable (0),
        no (1),
        nc (2)
    }
    MAX-ACCESS read-write
    STATUS current
    DESCRIPTION
    "The type of contactor for LLVD 6."
    ::= { batteryManagementParameter 48 }
  -- 1.3.6.1.4.1.39553.10.3.5.49
    llvd7contactorType OBJECT-TYPE
    SYNTAX INTEGER {
        biStable (0),
        no (1),
        nc (2)
    }
    MAX-ACCESS read-write
    STATUS current
    DESCRIPTION
    "The type of contactor for LLVD 7."
    ::= { batteryManagementParameter 49 }
  -- 1.3.6.1.4.1.39553.10.3.5.50
    llvd8contactorType OBJECT-TYPE
    SYNTAX INTEGER {
        biStable (0),
        no (1),
        nc (2)
    }
    MAX-ACCESS read-write
    STATUS current
    DESCRIPTION
    "The type of contactor for LLVD 8."
    ::= { batteryManagementParameter 50 }
  -- 1.3.6.1.4.1.39553.10.3.5.51
    llvd1VoltageEnableOption OBJECT-TYPE
    SYNTAX INTEGER {
        disable (0),
        enable (1)
    }
    MAX-ACCESS read-write
    STATUS current
    DESCRIPTION
    "The enable option for LLVD 1 function with bus voltage."
    ::= { batteryManagementParameter 51 }
  -- 1.3.6.1.4.1.39553.10.3.5.52
    llvd2VoltageEnableOption OBJECT-TYPE
    SYNTAX INTEGER {
        disable (0),
        enable (1)
    }
    MAX-ACCESS read-write
    STATUS current
    DESCRIPTION
    "The enable option for LLVD 2 function with bus voltage."
    ::= { batteryManagementParameter 52 }
  -- 1.3.6.1.4.1.39553.10.3.5.53
    llvd3VoltageEnableOption OBJECT-TYPE
    SYNTAX INTEGER {
        disable (0),
        enable (1)
    }
    MAX-ACCESS read-write
    STATUS current
    DESCRIPTION
    "The enable option for LLVD 3 function with bus voltage."
    ::= { batteryManagementParameter 53 }
  -- 1.3.6.1.4.1.39553.10.3.5.54
    llvd4VoltageEnableOption OBJECT-TYPE
    SYNTAX INTEGER {
        disable (0),
        enable (1)
    }
    MAX-ACCESS read-write
    STATUS current
    DESCRIPTION
    "The enable option for LLVD 4 function with bus voltage."
    ::= { batteryManagementParameter 54 }
  -- 1.3.6.1.4.1.39553.10.3.5.55
    llvd5VoltageEnableOption OBJECT-TYPE
    SYNTAX INTEGER {
        disable (0),
        enable (1)
    }
    MAX-ACCESS read-write
    STATUS current
    DESCRIPTION
    "The enable option for LLVD 5 function with bus voltage."
    ::= { batteryManagementParameter 55 }
  -- 1.3.6.1.4.1.39553.10.3.5.56
    llvd6VoltageEnableOption OBJECT-TYPE
    SYNTAX INTEGER {
        disable (0),
        enable (1)
    }
    MAX-ACCESS read-write
    STATUS current
    DESCRIPTION
    "The enable option for LLVD 6 function with bus voltage."
    ::= { batteryManagementParameter 56 }
  -- 1.3.6.1.4.1.39553.10.3.5.57
    llvd7VoltageEnableOption OBJECT-TYPE
    SYNTAX INTEGER {
        disable (0),
        enable (1)
    }
    MAX-ACCESS read-write
    STATUS current
    DESCRIPTION
    "The enable option for LLVD 7 function with bus voltage."
    ::= { batteryManagementParameter 57 }
  -- 1.3.6.1.4.1.39553.10.3.5.58
    llvd8VoltageEnableOption OBJECT-TYPE
    SYNTAX INTEGER {
        disable (0),
        enable (1)
    }
    MAX-ACCESS read-write
    STATUS current
    DESCRIPTION
    "The enable option for LLVD 8 function with bus voltage."
    ::= { batteryManagementParameter 58 }
  -- 1.3.6.1.4.1.39553.10.3.5.59
    llvd1VoltageSet OBJECT-TYPE
    SYNTAX INTEGER
    MAX-ACCESS read-write
    STATUS current
    DESCRIPTION
    "The voltage setted as a condition for LLVD 1 function.
     Voltage range:30V..Reconnect Voltage-5;default:44V;
     The actual value = the receive data/100.
     The unit of actual value is V."
    ::= { batteryManagementParameter 59 }
  -- 1.3.6.1.4.1.39553.10.3.5.60
    llvd2VoltageSet OBJECT-TYPE
    SYNTAX INTEGER
    MAX-ACCESS read-write
    STATUS current
    DESCRIPTION
    "The voltage setted as a condition for LLVD 2 function.
     Voltage range:30V..Reconnect Voltage-5;default:44V;
     The actual value = the receive data/100.
     The unit of actual value is V."
    ::= { batteryManagementParameter 60 }
  -- 1.3.6.1.4.1.39553.10.3.5.61
    llvd3VoltageSet OBJECT-TYPE
    SYNTAX INTEGER
    MAX-ACCESS read-write
    STATUS current
    DESCRIPTION
    "The voltage setted as a condition for LLVD 3 function.
     Voltage range:30V..Reconnect Voltage-5;default:44V;
     The actual value = the receive data/100.
     The unit of actual value is V."
    ::= { batteryManagementParameter 61 }
  -- 1.3.6.1.4.1.39553.10.3.5.62
    llvd4VoltageSet OBJECT-TYPE
    SYNTAX INTEGER
    MAX-ACCESS read-write
    STATUS current
    DESCRIPTION
    "The voltage setted as a condition for LLVD 4 function.
     Voltage range:30V..Reconnect Voltage-5;default:44V;
     The actual value = the receive data/100.
     The unit of actual value is V."
    ::= { batteryManagementParameter 62 }
  -- 1.3.6.1.4.1.39553.10.3.5.63
    llvd5VoltageSet OBJECT-TYPE
    SYNTAX INTEGER
    MAX-ACCESS read-write
    STATUS current
    DESCRIPTION
    "The voltage setted as a condition for LLVD 5 function.
     Voltage range:30V..Reconnect Voltage-5;default:44V;
     The actual value = the receive data/100.
     The unit of actual value is V."
    ::= { batteryManagementParameter 63 }
  -- 1.3.6.1.4.1.39553.10.3.5.64
    llvd6VoltageSet OBJECT-TYPE
    SYNTAX INTEGER
    MAX-ACCESS read-write
    STATUS current
    DESCRIPTION
    "The voltage setted as a condition for LLVD 6 function.
     Voltage range:30V..Reconnect Voltage-5;default:44V;
     The actual value = the receive data/100.
     The unit of actual value is V."
    ::= { batteryManagementParameter 64 }
  -- 1.3.6.1.4.1.39553.10.3.5.65
    llvd7VoltageSet OBJECT-TYPE
    SYNTAX INTEGER
    MAX-ACCESS read-write
    STATUS current
    DESCRIPTION
    "The voltage setted as a condition for LLVD 7 function.
     Voltage range:30V..Reconnect Voltage-5;default:44V;
     The actual value = the receive data/100.
     The unit of actual value is V."
    ::= { batteryManagementParameter 65 }
  -- 1.3.6.1.4.1.39553.10.3.5.66
    llvd8VoltageSet OBJECT-TYPE
    SYNTAX INTEGER
    MAX-ACCESS read-write
    STATUS current
    DESCRIPTION
    "The voltage setted as a condition for LLVD 8 function.
     Voltage range:30V..Reconnect Voltage-5;default:44V;
     The actual value = the receive data/100.
     The unit of actual value is V."
    ::= { batteryManagementParameter 66 }
  -- 1.3.6.1.4.1.39553.10.3.5.67
    llvd1TimeEnableOption OBJECT-TYPE
    SYNTAX INTEGER {
        disable (0),
        enable (1)
    }
    MAX-ACCESS read-write
    STATUS current
    DESCRIPTION
    "The enable option for LLVD 1 function with time."
    ::= { batteryManagementParameter 67 }
  -- 1.3.6.1.4.1.39553.10.3.5.68
    llvd2TimeEnableOption OBJECT-TYPE
    SYNTAX INTEGER {
        disable (0),
        enable (1)
    }
    MAX-ACCESS read-write
    STATUS current
    DESCRIPTION
    "The enable option for LLVD 2 function with time."
    ::= { batteryManagementParameter 68 }
  -- 1.3.6.1.4.1.39553.10.3.5.69
    llvd3TimeEnableOption OBJECT-TYPE
    SYNTAX INTEGER {
        disable (0),
        enable (1)
    }
    MAX-ACCESS read-write
    STATUS current
    DESCRIPTION
    "The enable option for LLVD 3 function with time."
    ::= { batteryManagementParameter 69 }
  -- 1.3.6.1.4.1.39553.10.3.5.70
    llvd4TimeEnableOption OBJECT-TYPE
    SYNTAX INTEGER {
        disable (0),
        enable (1)
    }
    MAX-ACCESS read-write
    STATUS current
    DESCRIPTION
    "The enable option for LLVD 4 function with time."
    ::= { batteryManagementParameter 70 }
  -- 1.3.6.1.4.1.39553.10.3.5.71
    llvd5TimeEnableOption OBJECT-TYPE
    SYNTAX INTEGER {
        disable (0),
        enable (1)
    }
    MAX-ACCESS read-write
    STATUS current
    DESCRIPTION
    "The enable option for LLVD 5 function with time."
    ::= { batteryManagementParameter 71 }
  -- 1.3.6.1.4.1.39553.10.3.5.72
    llvd6TimeEnableOption OBJECT-TYPE
    SYNTAX INTEGER {
        disable (0),
        enable (1)
    }
    MAX-ACCESS read-write
    STATUS current
    DESCRIPTION
    "The enable option for LLVD 6 function with time."
    ::= { batteryManagementParameter 72 }
  -- 1.3.6.1.4.1.39553.10.3.5.73
    llvd7TimeEnableOption OBJECT-TYPE
    SYNTAX INTEGER {
        disable (0),
        enable (1)
    }
    MAX-ACCESS read-write
    STATUS current
    DESCRIPTION
    "The enable option for LLVD 7 function with time."
    ::= { batteryManagementParameter 73 }
  -- 1.3.6.1.4.1.39553.10.3.5.74
    llvd8TimeEnableOption OBJECT-TYPE
    SYNTAX INTEGER {
        disable (0),
        enable (1)
    }
    MAX-ACCESS read-write
    STATUS current
    DESCRIPTION
    "The enable option for LLVD 8 function with time."
    ::= { batteryManagementParameter 74 }
  -- 1.3.6.1.4.1.39553.10.3.5.75
    llvd1TimeSet OBJECT-TYPE
    SYNTAX INTEGER(1..1000)
    MAX-ACCESS read-write
    STATUS current
    DESCRIPTION
    "The time setted as a condition for LLVD 1 function.
     The actual value = the receive data.
     The unit of actual value is minute."
    ::= { batteryManagementParameter 75 }
  -- 1.3.6.1.4.1.39553.10.3.5.76
    llvd2TimeSet OBJECT-TYPE
    SYNTAX INTEGER(1..1000)
    MAX-ACCESS read-write
    STATUS current
    DESCRIPTION
    "The time setted as a condition for LLVD 2 function.
     The actual value = the receive data.
     The unit of actual value is minute."
    ::= { batteryManagementParameter 76 }
  -- 1.3.6.1.4.1.39553.10.3.5.77
    llvd3TimeSet OBJECT-TYPE
    SYNTAX INTEGER(1..1000)
    MAX-ACCESS read-write
    STATUS current
    DESCRIPTION
    "The time setted as a condition for LLVD 3 function.
     The actual value = the receive data.
     The unit of actual value is minute."
    ::= { batteryManagementParameter 77 }
  -- 1.3.6.1.4.1.39553.10.3.5.78
    llvd4TimeSet OBJECT-TYPE
    SYNTAX INTEGER(1..1000)
    MAX-ACCESS read-write
    STATUS current
    DESCRIPTION
    "The time setted as a condition for LLVD 4 function.
     The actual value = the receive data.
     The unit of actual value is minute."
    ::= { batteryManagementParameter 78 }
  -- 1.3.6.1.4.1.39553.10.3.5.79
    llvd5TimeSet OBJECT-TYPE
    SYNTAX INTEGER(1..1000)
    MAX-ACCESS read-write
    STATUS current
    DESCRIPTION
    "The time setted as a condition for LLVD 5 function.
     The actual value = the receive data.
     The unit of actual value is minute."
    ::= { batteryManagementParameter 79 }
  -- 1.3.6.1.4.1.39553.10.3.5.80
    llvd6TimeSet OBJECT-TYPE
    SYNTAX INTEGER(1..1000)
    MAX-ACCESS read-write
    STATUS current
    DESCRIPTION
    "The time setted as a condition for LLVD 6 function.
     The actual value = the receive data.
     The unit of actual value is minute."
    ::= { batteryManagementParameter 80 }
  -- 1.3.6.1.4.1.39553.10.3.5.81
    llvd7TimeSet OBJECT-TYPE
    SYNTAX INTEGER(1..1000)
    MAX-ACCESS read-write
    STATUS current
    DESCRIPTION
    "The time setted as a condition for LLVD 7 function.
     The actual value = the receive data.
     The unit of actual value is minute."
    ::= { batteryManagementParameter 81 }
  -- 1.3.6.1.4.1.39553.10.3.5.82
    llvd8TimeSet OBJECT-TYPE
    SYNTAX INTEGER(1..1000)
    MAX-ACCESS read-write
    STATUS current
    DESCRIPTION
    "The time setted as a condition for LLVD 8 function.
     The actual value = the receive data.
     The unit of actual value is minute."
    ::= { batteryManagementParameter 82 }
  -- 1.3.6.1.4.1.39553.10.3.5.83
    blvdEnableOption OBJECT-TYPE
    SYNTAX INTEGER {
        none (0),
        disable (1),
        enable (2)
    }
    MAX-ACCESS read-write
    STATUS current
    DESCRIPTION
    "The enable option for BLVD function."
    ::= { batteryManagementParameter 83 }
  -- 1.3.6.1.4.1.39553.10.3.5.84
    blvdContactorType OBJECT-TYPE
    SYNTAX INTEGER {
        biStable (0),
        no (1),
        nc (2)
    }
    MAX-ACCESS read-write
    STATUS current
    DESCRIPTION
    "the type of BLVD contactor."
    ::= { batteryManagementParameter 84 }
  -- 1.3.6.1.4.1.39553.10.3.5.85
    blvdVoltageEnableOption OBJECT-TYPE
    SYNTAX INTEGER {
        disable (0),
        enable (1)
    }
    MAX-ACCESS read-write
    STATUS current
    DESCRIPTION
    "The enable option for BLVD function with bus voltage."
    ::= { batteryManagementParameter 85 }
  -- 1.3.6.1.4.1.39553.10.3.5.86
    blvdVoltage OBJECT-TYPE
    SYNTAX INTEGER
    MAX-ACCESS read-write
    STATUS current
    DESCRIPTION
     "The bus voltage as a condition for BLVD function.
      The actual value = the receive data/100.
      The unit of actual value is V.
      Voltage range:30V..Reconnect Voltage-5."
    ::= { batteryManagementParameter 86 }
  -- 1.3.6.1.4.1.39553.10.3.5.87
    blvdCapacityEnableOption OBJECT-TYPE
    SYNTAX INTEGER {
        disable (0),
        enable (1)
    }
    MAX-ACCESS read-write
    STATUS current
    DESCRIPTION
    "The enable option for BLVD function with battery capacity."
    ::= { batteryManagementParameter 87 }
  -- 1.3.6.1.4.1.39553.10.3.5.88
    blvdCapacity OBJECT-TYPE
    SYNTAX INTEGER(10000..100000)
    MAX-ACCESS read-write
    STATUS current
    DESCRIPTION
     "The battery residual capacity as a condition for BLVD function.
      The actual value = the receive data/1000.
      The unit of actual value is %.
      Capacity range:10%..100%."
    ::= { batteryManagementParameter 88 }
  -- 1.3.6.1.4.1.39553.10.3.5.89
    blvdTimeEnableOption OBJECT-TYPE
    SYNTAX INTEGER {
        disable (0),
        enable (1)
    }
    MAX-ACCESS read-write
    STATUS current
    DESCRIPTION
    "The enable option for BLVD function with time."
    ::= { batteryManagementParameter 89 }
  -- 1.3.6.1.4.1.39553.10.3.5.90
    blvdTime OBJECT-TYPE
    SYNTAX INTEGER(0..1000)
    MAX-ACCESS read-write
    STATUS current
    DESCRIPTION
     "The time as a condition for BLVD function.
      The actual value = the receive data.
      The unit of actual value is minute.
      Time range:0..1000."
    ::= { batteryManagementParameter 90 }
  -- 1.3.6.1.4.1.39553.10.3.5.91
    blvdHighTemperatureEnableOption OBJECT-TYPE
    SYNTAX INTEGER {
        disable (0),
        enable (1)
    }
    MAX-ACCESS read-write
    STATUS current
    DESCRIPTION
     "The enable option for BLVD function with battery high temperature."
    ::= { batteryManagementParameter 91 }
  -- 1.3.6.1.4.1.39553.10.3.5.92
    blvdHighTemperature OBJECT-TYPE
    SYNTAX INTEGER
    MAX-ACCESS read-write
    STATUS current
    DESCRIPTION
     "The battery high temperature as a condition for BLVD function.
      The actual value = the receive data/100.
      The unit of actual value is degree centigrade.
      Temperature range:The minimum value between 30 degree centigrade and Reconnect High Temperature+4 .. 66."
    ::= { batteryManagementParameter 92 }
  -- 1.3.6.1.4.1.39553.10.3.5.93
    blvdLowTemperatureEnableOpyin OBJECT-TYPE
    SYNTAX INTEGER {
        disable (0),
        enable (1)
    }
    MAX-ACCESS read-write
    STATUS current
    DESCRIPTION
     "The enable option for BLVD function with battery low temperature."
    ::= { batteryManagementParameter 93 }
  -- 1.3.6.1.4.1.39553.10.3.5.94
    blvdLowTemperature OBJECT-TYPE
    SYNTAX INTEGER
    MAX-ACCESS read-write
    STATUS current
    DESCRIPTION
     "The battery low temperature as a condition for BLVD function.
      The actual value = the receive data/100.
      The unit of actual value is degree centigrade.
      Temperature range:-33 .. The maximum value between 16 degree centigrade and Reconnect Low Temperature - 4."
    ::= { batteryManagementParameter 94 }
  -- 1.3.6.1.4.1.39553.10.3.5.95
    blvdHighBusVoltageEnableOption OBJECT-TYPE
    SYNTAX INTEGER {
        disable (0),
        enable (1)
    }
    MAX-ACCESS read-write
    STATUS current
    DESCRIPTION
     "The enable option for BLVD function with high bus voltage."
    ::= { batteryManagementParameter 95 }
  -- 1.3.6.1.4.1.39553.10.3.5.96
    blvdHighBusVoltage OBJECT-TYPE
    SYNTAX INTEGER(5720..6000)
    MAX-ACCESS read-write
    STATUS current
    DESCRIPTION
     "The high bus voltage as a condition for BLVD function.
      The actual value = the receive data/100.
      The unit of actual value is V.
      Voltage range:57.2V .. 60V."
    ::= { batteryManagementParameter 96 }
  -- 1.3.6.1.4.1.39553.10.3.5.97
    batteryTestEndTime OBJECT-TYPE
    SYNTAX INTEGER(5..1440)
    MAX-ACCESS read-write
    STATUS current
    DESCRIPTION
     "The battery test end time.
      The actual value = the receive data.
      The unit of actual value is minute.
      Time range:5min .. 1440min."
    ::= { batteryManagementParameter 97 }
  -- 1.3.6.1.4.1.39553.10.3.5.98
    batteryCycleTestEnableOption OBJECT-TYPE
    SYNTAX INTEGER {
        disable (0),
        enable (1)
    }
    MAX-ACCESS read-write
    STATUS current
    DESCRIPTION
     "The enable option for battery cycle test function."
    ::= { batteryManagementParameter 98 }
  -- 1.3.6.1.4.1.39553.10.3.5.99
    batteryCycleTestTime OBJECT-TYPE
    SYNTAX INTEGER(1..200)
    MAX-ACCESS read-write
    STATUS current
    DESCRIPTION
     "The time for battery cycle test function.
      The actual value = the receive data.
      The unit of actual value is minute.
      Time range:1min .. 200min."
    ::= { batteryManagementParameter 99 }
  -- 1.3.6.1.4.1.39553.10.3.5.100
    batteryCycleTestPeriod OBJECT-TYPE
    SYNTAX INTEGER(1..8760)
    MAX-ACCESS read-write
    STATUS current
    DESCRIPTION
     "The period for battery cycle test function.
      The actual value = the receive data.
      The unit of actual value is hour.
      Time range:1hour .. 8760hour."
    ::= { batteryManagementParameter 100 }
  -- 1.3.6.1.4.1.39553.10.3.5.101
    batteryFloatVoltage OBJECT-TYPE
    SYNTAX INTEGER
    MAX-ACCESS read-write
    STATUS current
    DESCRIPTION
     "The voltage for battery float.
      The actual value = the receive data/100.
      The unit of actual value is V.
      voltage range:Boost Voltage .. 42V."
    ::= { batteryManagementParameter 101 }
  -- 1.3.6.1.4.1.39553.10.3.5.102
    batteryBoostVoltage OBJECT-TYPE
    SYNTAX INTEGER
    MAX-ACCESS read-write
    STATUS current
    DESCRIPTION
     "The voltage for battery boost.
      The actual value = the receive data/100.
      The unit of actual value is V.
      voltage range:60V .. Float Voltage."
    ::= { batteryManagementParameter 102 }
  -- 1.3.6.1.4.1.39553.10.3.5.103
    batteryTestEndVoltage OBJECT-TYPE
    SYNTAX INTEGER
    MAX-ACCESS read-write
    STATUS current
    DESCRIPTION
     "The voltage as a condition for battery test end function.
      The actual value = the receive data/100.
      The unit of actual value is V.
      Voltage range:Boost voltage .. DC under voltage."
    ::= { batteryManagementParameter 103 }
  -- 1.3.6.1.4.1.39553.10.3.5.104
    batteryTestEndCapacity OBJECT-TYPE
    SYNTAX INTEGER(50000..99000)
    MAX-ACCESS read-write
    STATUS current
    DESCRIPTION
     "The residual capacity as a condition for battery test end function.
      The actual value = the receive data/1000.
      The unit of actual value is %.
      Capacity range:50% .. 99%."
    ::= { batteryManagementParameter 104 }
  -- 1.3.6.1.4.1.39553.10.3.5.105
    batteryConstantCurrentTestEnableOption OBJECT-TYPE
    SYNTAX INTEGER {
        disable (0),
        enable (1)
    }
    MAX-ACCESS read-write
    STATUS current
    DESCRIPTION
     "The enable option for battery constant current test function."
    ::= { batteryManagementParameter 105 }
  -- 1.3.6.1.4.1.39553.10.3.5.106
    batteryConstantCurrentTestCurrent OBJECT-TYPE
    SYNTAX INTEGER(1000..1500000)
    MAX-ACCESS read-write
    STATUS current
    DESCRIPTION
     "The current as a condition for battery constant current test function.
      The actual value = the receive data/1000.
      The unit of actual value is A.
      Current range:1A .. 1500A."
    ::= { batteryManagementParameter 106 }
  -- 1.3.6.1.4.1.39553.10.3.5.107
    batteryChargeCurrentLimit OBJECT-TYPE
    SYNTAX INTEGER(100 .. 400)
    MAX-ACCESS read-write
    STATUS current
    DESCRIPTION
    "The factor of battery charge limit with current.
     The actual value = the receive data/1000.
     The unit of actual value is C10.
     Value range:0.1C10 .. 0.4C10."
    ::= { batteryManagementParameter 107 }
  -- 1.3.6.1.4.1.39553.10.3.5.108
    batteryChargeOverCurrent OBJECT-TYPE
    SYNTAX INTEGER(100 .. 3000)
    MAX-ACCESS read-write
    STATUS current
    DESCRIPTION
    "The factor of battery over charge with current.
     The actual value = the receive data/1000.
     The unit of actual value is C10.
     Value range:0.1C10 .. 3C10."
    ::= { batteryManagementParameter 108 }
  -- 1.3.6.1.4.1.39553.10.3.5.109
    batteryConstantBoostStartCurrent OBJECT-TYPE
    SYNTAX INTEGER(2..20)
    MAX-ACCESS read-write
    STATUS current
    DESCRIPTION
    "The factor of battery constant boost charge with start current.
     The actual value = the receive data/1000.
     The unit of actual value is C10.
     Value range:0.002C10 .. 0.02C10."
    ::= { batteryManagementParameter 109 }
  -- 1.3.6.1.4.1.39553.10.3.5.110
    batteryConstantBoostMaximumCurrent OBJECT-TYPE
    SYNTAX INTEGER(8..80)
    MAX-ACCESS read-write
    STATUS current
    DESCRIPTION
    "The factor of battery constant boost charge with maximum current.
     The actual value = the receive data/1000.
     The unit of actual value is C10.
     Value range:0.008C10 .. 0.08C10."
    ::= { batteryManagementParameter 110 }
  -- 1.3.6.1.4.1.39553.10.3.5.111
    batteryConstantBoostKeepTime OBJECT-TYPE
    SYNTAX INTEGER(100..24000)
    MAX-ACCESS read-write
    STATUS current
    DESCRIPTION
    "The time of battery constant boost charge keeping.
     The actual value = the receive data/1000.
     The unit of actual value is hour.
     Time range:0.1h .. 24h."
    ::= { batteryManagementParameter 111 }
  -- 1.3.6.1.4.1.39553.10.3.5.112
    systemWorkMode OBJECT-TYPE
    SYNTAX INTEGER {
        auto (0),
        manual (1)
    }
    MAX-ACCESS read-write
    STATUS current
    DESCRIPTION
    "The mode of system work."
    ::= { batteryManagementParameter 112 }
  -- 1.3.6.1.4.1.39553.10.3.5.113
    autoBoostEnableOption OBJECT-TYPE
    SYNTAX INTEGER {
        disable (0),
        enable (1)
    }
    MAX-ACCESS read-write
    STATUS current
    DESCRIPTION
     "The enable option for battery auto boost charge function."
    ::= { batteryManagementParameter 113 }
  -- 1.3.6.1.4.1.39553.10.3.5.114
    autoBoostStartCurrent OBJECT-TYPE
    SYNTAX INTEGER(50..80)
    MAX-ACCESS read-write
    STATUS current
    DESCRIPTION
    "The start current for battery auto boost charge function.
     The actual value = the receive data/1000.
     The unit of actual value is C10.
     Value range:0.05C10 .. 0.08C10."
    ::= { batteryManagementParameter 114 }
  -- 1.3.6.1.4.1.39553.10.3.5.115
    autoBoostMinimumCapacity OBJECT-TYPE
    SYNTAX INTEGER(10000..95000)
    MAX-ACCESS read-write
    STATUS current
    DESCRIPTION
    "The minimum battery capacity for battery auto boost charge function.
     The actual value = the receive data/1000.
     The unit of actual value is %.
     Value range:10% .. 95%."
    ::= { batteryManagementParameter 115 }
  -- 1.3.6.1.4.1.39553.10.3.5.116
    autoBoostStartVoltage OBJECT-TYPE
    SYNTAX INTEGER(4400..5300)
    MAX-ACCESS read-write
    STATUS current
    DESCRIPTION
    "The voltage for battery auto boost charge function.
     The actual value = the receive data/100.
     The unit of actual value is V.
     Value range:44V .. 53V."
    ::= { batteryManagementParameter 116 }
  -- 1.3.6.1.4.1.39553.10.3.5.117
    boostProtectionTime OBJECT-TYPE
    SYNTAX INTEGER(100..48000)
    MAX-ACCESS read-write
    STATUS current
    DESCRIPTION
    "The time for battery boost charge protection.
     The actual value = the receive data/1000.
     The unit of actual value is hour.
     Time range:0.1h .. 48h."
    ::= { batteryManagementParameter 117 }
  -- 1.3.6.1.4.1.39553.10.3.5.118
    cycleBoostEnableOption OBJECT-TYPE
    SYNTAX INTEGER {
        disable (0),
        enable (1)
    }
    MAX-ACCESS read-write
    STATUS current
    DESCRIPTION
     "The enable option for battery cycle boost charge function."
    ::= { batteryManagementParameter 118 }
  -- 1.3.6.1.4.1.39553.10.3.5.119
    cycleBoostPeriod OBJECT-TYPE
    SYNTAX INTEGER(400..360000)
    MAX-ACCESS read-write
    STATUS current
    DESCRIPTION
    "The period for battery cycle boost charge.
     The actual value = the receive data/1000.
     The unit of actual value is day.
     Time range:0.4day .. 360day."
    ::= { batteryManagementParameter 119 }
  -- 1.3.6.1.4.1.39553.10.3.5.120
    cycleBoostTime OBJECT-TYPE
    SYNTAX INTEGER(100..24000)
    MAX-ACCESS read-write
    STATUS current
    DESCRIPTION
    "The time for battery cycle boost charge.
     The actual value = the receive data/1000.
     The unit of actual value is hour.
     Time range:0.1h .. 24h."
    ::= { batteryManagementParameter 120 }
  -- 1.3.6.1.4.1.39553.10.3.5.121
    battery1Capacity OBJECT-TYPE
    SYNTAX INTEGER(10000..5000000)
    MAX-ACCESS read-write
    STATUS current
    DESCRIPTION
    "The capacity of battery 1.
     The actual value = the receive data/1000.
     The unit of actual value is AH.
     Capacity range:10AH .. 5000AH."
    ::= { batteryManagementParameter 121 }
  -- 1.3.6.1.4.1.39553.10.3.5.122
    battery2Capacity OBJECT-TYPE
    SYNTAX INTEGER(10000..5000000)
    MAX-ACCESS read-write
    STATUS current
    DESCRIPTION
    "The capacity of battery 2.
     The actual value = the receive data/1000.
     The unit of actual value is AH.
     Capacity range:10AH .. 5000AH."
    ::= { batteryManagementParameter 122 }
  -- 1.3.6.1.4.1.39553.10.3.5.123
    battery3Capacity OBJECT-TYPE
    SYNTAX INTEGER(10000..5000000)
    MAX-ACCESS read-write
    STATUS current
    DESCRIPTION
    "The capacity of battery 3.
     The actual value = the receive data/1000.
     The unit of actual value is AH.
     Capacity range:10AH .. 5000AH."
    ::= { batteryManagementParameter 123 }
  -- 1.3.6.1.4.1.39553.10.3.5.124
    battery4Capacity OBJECT-TYPE
    SYNTAX INTEGER(10000..5000000)
    MAX-ACCESS read-write
    STATUS current
    DESCRIPTION
    "The capacity of battery 4.
     The actual value = the receive data/1000.
     The unit of actual value is AH.
     Capacity range:10AH .. 5000AH."
    ::= { batteryManagementParameter 124 }
  -- 1.3.6.1.4.1.39553.10.3.5.125
    battery5Capacity OBJECT-TYPE
    SYNTAX INTEGER(10000..5000000)
    MAX-ACCESS read-write
    STATUS current
    DESCRIPTION
    "The capacity of battery 5.
     The actual value = the receive data/1000.
     The unit of actual value is AH.
     Capacity range:10AH .. 5000AH."
    ::= { batteryManagementParameter 125 }
  -- 1.3.6.1.4.1.39553.10.3.5.126
    battery6Capacity OBJECT-TYPE
    SYNTAX INTEGER(10000..5000000)
    MAX-ACCESS read-write
    STATUS current
    DESCRIPTION
    "The capacity of battery 6.
     The actual value = the receive data/1000.
     The unit of actual value is AH.
     Capacity range:10AH .. 5000AH."
    ::= { batteryManagementParameter 126 }
  -- 1.3.6.1.4.1.39553.10.3.5.127
    battery7Capacity OBJECT-TYPE
    SYNTAX INTEGER(10000..5000000)
    MAX-ACCESS read-write
    STATUS current
    DESCRIPTION
    "The capacity of battery 7.
     The actual value = the receive data/1000.
     The unit of actual value is AH.
     Capacity range:10AH .. 5000AH."
    ::= { batteryManagementParameter 127 }
  -- 1.3.6.1.4.1.39553.10.3.5.128
    battery8Capacity OBJECT-TYPE
    SYNTAX INTEGER(10000..5000000)
    MAX-ACCESS read-write
    STATUS current
    DESCRIPTION
    "The capacity of battery 8.
     The actual value = the receive data/1000.
     The unit of actual value is AH.
     Capacity range:10AH .. 5000AH."
    ::= { batteryManagementParameter 128 }
  -- 1.3.6.1.4.1.39553.10.3.5.129
    battery1ResidualCapacity  OBJECT-TYPE
    SYNTAX INTEGER(100..100000)
    MAX-ACCESS read-write
    STATUS current
    DESCRIPTION
    "The residual capacity of battery 1.
     The actual value = the receive data/1000.
     The unit of actual value is %.
     Capacity range:0.1% .. 100%."
    ::= { batteryManagementParameter 129 }
  -- 1.3.6.1.4.1.39553.10.3.5.130
    battery2ResidualCapacity OBJECT-TYPE
    SYNTAX INTEGER(100..100000)
    MAX-ACCESS read-write
    STATUS current
    DESCRIPTION
    "The residual capacity of battery 2.
     The actual value = the receive data/1000.
     The unit of actual value is %.
     Capacity range:0.1% .. 100%."
    ::= { batteryManagementParameter 130 }
  -- 1.3.6.1.4.1.39553.10.3.5.131
    battery3ResidualCapacity OBJECT-TYPE
    SYNTAX INTEGER(100..100000)
    MAX-ACCESS read-write
    STATUS current
    DESCRIPTION
    "The residual capacity of battery 3.
     The actual value = the receive data/1000.
     The unit of actual value is %.
     Capacity range:0.1% .. 100%."
    ::= { batteryManagementParameter 131 }
  -- 1.3.6.1.4.1.39553.10.3.5.132
    battery4ResidualCapacity OBJECT-TYPE
    SYNTAX INTEGER(100..100000)
    MAX-ACCESS read-write
    STATUS current
    DESCRIPTION
    "The residual capacity of battery 4.
     The actual value = the receive data/1000.
     The unit of actual value is %.
     Capacity range:0.1% .. 100%."
    ::= { batteryManagementParameter 132 }
  -- 1.3.6.1.4.1.39553.10.3.5.133
    battery5ResidualCapacity OBJECT-TYPE
    SYNTAX INTEGER(100..100000)
    MAX-ACCESS read-write
    STATUS current
    DESCRIPTION
    "The residual capacity of battery 5.
     The actual value = the receive data/1000.
     The unit of actual value is %.
     Capacity range:0.1% .. 100%."
    ::= { batteryManagementParameter 133 }
  -- 1.3.6.1.4.1.39553.10.3.5.134
    battery6ResidualCapacity OBJECT-TYPE
    SYNTAX INTEGER(100..100000)
    MAX-ACCESS read-write
    STATUS current
    DESCRIPTION
    "The residual capacity of battery 6.
     The actual value = the receive data/1000.
     The unit of actual value is %.
     Capacity range:0.1% .. 100%."
    ::= { batteryManagementParameter 134 }
  -- 1.3.6.1.4.1.39553.10.3.5.135
    battery7ResidualCapacity OBJECT-TYPE
    SYNTAX INTEGER(100..100000)
    MAX-ACCESS read-write
    STATUS current
    DESCRIPTION
    "The residual capacity of battery 7.
     The actual value = the receive data/1000.
     The unit of actual value is %.
     Capacity range:0.1% .. 100%."
    ::= { batteryManagementParameter 135 }
  -- 1.3.6.1.4.1.39553.10.3.5.136
    battery8ResidualCapacity OBJECT-TYPE
    SYNTAX INTEGER(100..100000)
    MAX-ACCESS read-write
    STATUS current
    DESCRIPTION
    "The residual capacity of battery 1.
     The actual value = the receive data/1000.
     The unit of actual value is %.
     Capacity range:0.1% .. 100%."
    ::= { batteryManagementParameter 136 }
  -- 1.3.6.1.4.1.39553.10.3.5.137
    battery1ChargeEfficiency OBJECT-TYPE
    SYNTAX INTEGER(800..1000)
    MAX-ACCESS read-write
    STATUS current
    DESCRIPTION
    "The efficiency of battery 1 charge.
     The actual value = the receive data/1000.
     Efficiency range:0.8 .. 1."
    ::= { batteryManagementParameter 137 }
  -- 1.3.6.1.4.1.39553.10.3.5.138
    battery2ChargeEfficiency OBJECT-TYPE
    SYNTAX INTEGER(800..1000)
    MAX-ACCESS read-write
    STATUS current
    DESCRIPTION
    "The efficiency of battery 2 charge.
     The actual value = the receive data/1000.
     Efficiency range:0.8 .. 1."
    ::= { batteryManagementParameter 138 }
  -- 1.3.6.1.4.1.39553.10.3.5.139
    battery3ChargeEfficiency OBJECT-TYPE
    SYNTAX INTEGER(800..1000)
    MAX-ACCESS read-write
    STATUS current
    DESCRIPTION
    "The efficiency of battery 3 charge.
     The actual value = the receive data/1000.
     Efficiency range:0.8 .. 1."
    ::= { batteryManagementParameter 139 }
  -- 1.3.6.1.4.1.39553.10.3.5.140
    battery4ChargeEfficiency OBJECT-TYPE
    SYNTAX INTEGER(800..1000)
    MAX-ACCESS read-write
    STATUS current
    DESCRIPTION
    "The efficiency of battery 4 charge.
     The actual value = the receive data/1000.
     Efficiency range:0.8 .. 1."
    ::= { batteryManagementParameter 140 }
  -- 1.3.6.1.4.1.39553.10.3.5.141
    battery5ChargeEfficiency OBJECT-TYPE
    SYNTAX INTEGER(800..1000)
    MAX-ACCESS read-write
    STATUS current
    DESCRIPTION
    "The efficiency of battery 5 charge.
     The actual value = the receive data/1000.
     Efficiency range:0.8 .. 1."
    ::= { batteryManagementParameter 141 }
  -- 1.3.6.1.4.1.39553.10.3.5.142
    battery6ChargeEfficiency OBJECT-TYPE
    SYNTAX INTEGER(800..1000)
    MAX-ACCESS read-write
    STATUS current
    DESCRIPTION
    "The efficiency of battery 6 charge.
     The actual value = the receive data/1000.
     Efficiency range:0.8 .. 1."
    ::= { batteryManagementParameter 142 }
  -- 1.3.6.1.4.1.39553.10.3.5.143
    battery7ChargeEfficiency OBJECT-TYPE
    SYNTAX INTEGER(800..1000)
    MAX-ACCESS read-write
    STATUS current
    DESCRIPTION
    "The efficiency of battery 7 charge.
     The actual value = the receive data/1000.
     Efficiency range:0.8 .. 1."
    ::= { batteryManagementParameter 143 }
  -- 1.3.6.1.4.1.39553.10.3.5.144
    battery8ChargeEfficiency OBJECT-TYPE
    SYNTAX INTEGER(800..1000)
    MAX-ACCESS read-write
    STATUS current
    DESCRIPTION
    "The efficiency of battery 8 charge.
     The actual value = the receive data/1000.
     Efficiency range:0.8 .. 1."
    ::= { batteryManagementParameter 144 }
  -- 1.3.6.1.4.1.39553.10.3.5.145
    batteryTempCompensationEnableOption OBJECT-TYPE
    SYNTAX INTEGER {
        disable (0),
        enable (1)
    }
    MAX-ACCESS read-write
    STATUS current
    DESCRIPTION
     "The enable option for battery temperature compensation function."
    ::= { batteryManagementParameter 145 }
  -- 1.3.6.1.4.1.39553.10.3.5.146
    batteryTempCompensationCenter OBJECT-TYPE
    SYNTAX INTEGER(10000..40000)
    MAX-ACCESS read-write
    STATUS current
    DESCRIPTION
     "The temperature compensation reference point for battery.
      The actual value = the receive data/1000.
      The unit of actual value is degree centigrade.
      Value range:10..40."
    ::= { batteryManagementParameter 146 }
  -- 1.3.6.1.4.1.39553.10.3.5.147
    batteryTempCompensationCoefficient OBJECT-TYPE
    SYNTAX INTEGER(0..500000)
    MAX-ACCESS read-write
    STATUS current
    DESCRIPTION
     "The temperature compensation coefficient for battery.
      The actual value = the receive data/1000.
      The unit of actual value is mv/(degree centigrade).
      Efficiency range:0.. 500."
    ::= { batteryManagementParameter 147 }
  -- 1.3.6.1.4.1.39553.10.3.5.148
    rectifierMaximumCurrentLimit OBJECT-TYPE
    SYNTAX INTEGER(10000..120000)
    MAX-ACCESS read-write
    STATUS current
    DESCRIPTION
     "The maximum current limit for rectifier.
      The actual value = the receive data/1000.
      The unit of actual value is %.
      Value range:10% .. 120%."
    ::= { batteryManagementParameter 148 }
    -- 1.3.6.1.4.1.39553.10.3.5.149
    batteryReconnectInterdependency OBJECT-TYPE
    SYNTAX INTEGER {
        dependent (0),
        independent (1)
    }
    MAX-ACCESS read-write
    STATUS current
    DESCRIPTION
     "The interdependency for mains input with battery reconnect."
    ::= { batteryManagementParameter 149 }
  -- 1.3.6.1.4.1.39553.10.3.5.150
    batteryDisconnectInterdependency OBJECT-TYPE
    SYNTAX INTEGER {
        dependent (0),
        independent (1)
    }
    MAX-ACCESS read-write
    STATUS current
    DESCRIPTION
     "The interdependency for mains input with battery disconnect."
    ::= { batteryManagementParameter 150 }
  -- 1.3.6.1.4.1.39553.10.3.5.151
    batteryReconnectVoltage OBJECT-TYPE
    SYNTAX INTEGER
    MAX-ACCESS read-write
    STATUS current
    DESCRIPTION
     "The voltage as a condition for battery reconnect function.
      The actual value = the receive data/100.
      The unit of actual value is V.
      Value range:Disconnect Voltage+5 .. 60V."
    ::= { batteryManagementParameter 151 }
  -- 1.3.6.1.4.1.39553.10.3.5.152
    llvd1ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 152 }
  -- 1.3.6.1.4.1.39553.10.3.5.153
    llvd2ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 153 }
  -- 1.3.6.1.4.1.39553.10.3.5.154
    llvd3ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 154 }
  -- 1.3.6.1.4.1.39553.10.3.5.155
    llvd4ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 155 }
  -- 1.3.6.1.4.1.39553.10.3.5.156
    llvd5ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 156 }
  -- 1.3.6.1.4.1.39553.10.3.5.157
    llvd6ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 157 }
  -- 1.3.6.1.4.1.39553.10.3.5.158
    llvd7ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 158 }
  -- 1.3.6.1.4.1.39553.10.3.5.159
    llvd8ReconnectVoltage OBJECT-TYPE
    SYNTAX INTEGER
    MAX-ACCESS read-write
    STATUS current
    DESCRIPTION
     "The voltage as a condition for LLVD function.
      The actual value = the receive data/100.
      The unit of actual value is V.
      Value range:Disconnect Voltage+5 .. 60V."
    ::= { batteryManagementParameter 159 }
  -- 1.3.6.1.4.1.39553.10.3.5.160
    blvdReconnectDelay OBJECT-TYPE
    SYNTAX INTEGER(0..900)
    MAX-ACCESS read-write
    STATUS current
    DESCRIPTION
     "The delay time for BLVD Reconnect function.
      The actual value = the receive data.
      The unit of actual value is second.
      Delay time range:0 .. 900s."
    ::= { batteryManagementParameter 160 }
  -- 1.3.6.1.4.1.39553.10.3.5.161
    llvd1ReconnectDelay OBJECT-TYPE
    SYNTAX INTEGER(0..900)
    MAX-ACCESS read-write
    STATUS current
    DESCRIPTION
     "The delay time for LLVD 1 Reconnect function.
      The actual value = the receive data.
      The unit of actual value is second.
      Delay time range:0 .. 900s."
    ::= { batteryManagementParameter 161 }
  -- 1.3.6.1.4.1.39553.10.3.5.162
    llvd2ReconnectDelay OBJECT-TYPE
    SYNTAX INTEGER(0..900)
    MAX-ACCESS read-write
    STATUS current
    DESCRIPTION
     "The delay time for LLVD 2 Reconnect function.
      The actual value = the receive data.
      The unit of actual value is second.
      Delay time range:0 .. 900s."
    ::= { batteryManagementParameter 162 }
  -- 1.3.6.1.4.1.39553.10.3.5.163
    llvd3ReconnectDelay OBJECT-TYPE
    SYNTAX INTEGER
    MAX-ACCESS read-write
    STATUS current
    DESCRIPTION
     "The delay time for LLVD 3 Reconnect function.
      The actual value = the receive data.
      The unit of actual value is second.
      Delay time range:0 .. 900s."
    ::= { batteryManagementParameter 163 }
  -- 1.3.6.1.4.1.39553.10.3.5.164
    llvd4ReconnectDelay OBJECT-TYPE
    SYNTAX INTEGER
    MAX-ACCESS read-write
    STATUS current
    DESCRIPTION
     "The delay time for LLVD 4 Reconnect function.
      The actual value = the receive data.
      The unit of actual value is second.
      Delay time range:0 .. 900s."
    ::= { batteryManagementParameter 164 }
  -- 1.3.6.1.4.1.39553.10.3.5.165
    llvd5ReconnectDelay OBJECT-TYPE
    SYNTAX INTEGER
    MAX-ACCESS read-write
    STATUS current
    DESCRIPTION
     "The delay time for LLVD 5 Reconnect function.
      The actual value = the receive data.
      The unit of actual value is second.
      Delay time range:0 .. 900s."
    ::= { batteryManagementParameter 165 }
  -- 1.3.6.1.4.1.39553.10.3.5.166
    llvd6ReconnectDelay OBJECT-TYPE
    SYNTAX INTEGER
    MAX-ACCESS read-write
    STATUS current
    DESCRIPTION
     "The delay time for LLVD 6 Reconnect function.
      The actual value = the receive data.
      The unit of actual value is second.
      Delay time range:0 .. 900s."
    ::= { batteryManagementParameter 166 }
  -- 1.3.6.1.4.1.39553.10.3.5.167
    llvd7ReconnectDelay OBJECT-TYPE
    SYNTAX INTEGER
    MAX-ACCESS read-write
    STATUS current
    DESCRIPTION
     "The delay time for LLVD 7 Reconnect function.
      The actual value = the receive data.
      The unit of actual value is second.
      Delay time range:0 .. 900s."
    ::= { batteryManagementParameter 167 }
  -- 1.3.6.1.4.1.39553.10.3.5.168
    llvd8ReconnectDelay OBJECT-TYPE
    SYNTAX INTEGER
    MAX-ACCESS read-write
    STATUS current
    DESCRIPTION
     "The delay time for LLVD 8 Reconnect function.
      The actual value = the receive data.
      The unit of actual value is second.
      Delay time range:0 .. 900s."
    ::= { batteryManagementParameter 168 }
  -- 1.3.6.1.4.1.39553.10.3.5.169
    batteryManageMode OBJECT-TYPE
    SYNTAX INTEGER {
        current (0),
        voltage (1),
        disable (2)
    }
    MAX-ACCESS read-write
    STATUS current
    DESCRIPTION
     "The mode for battery manage."
    ::= { batteryManagementParameter 169 }
  -- 1.3.6.1.4.1.39553.10.3.5.170
    rectifierOVSDPoint OBJECT-TYPE
    SYNTAX INTEGER(5720..5970)
    MAX-ACCESS read-write
    STATUS current
    DESCRIPTION
     "The OVSD point for rectifier.
      The actual value = the receive data/100.
      The unit of actual value is V.
      Value range:57.2V .. 59.7V."
    ::= { batteryManagementParameter 170 }
  -- 1.3.6.1.4.1.39553.10.3.5.171
    llvd1HighTempEnableOption OBJECT-TYPE
    SYNTAX INTEGER {
        disable (0),
        enable (1)
    }
    MAX-ACCESS read-write
    STATUS current
    DESCRIPTION
     "The enable option for LLVD 1 function with high temperature."
    ::= { batteryManagementParameter 171 }
  -- 1.3.6.1.4.1.39553.10.3.5.172
    llvd2HighTempEnableOption OBJECT-TYPE
    SYNTAX INTEGER {
        disable (0),
        enable (1)
    }
    MAX-ACCESS read-write
    STATUS current
    DESCRIPTION
     "The enable option for LLVD 2 function with high temperature."
    ::= { batteryManagementParameter 172 }
  -- 1.3.6.1.4.1.39553.10.3.5.173
    llvd3HighTempEnableOption OBJECT-TYPE
    SYNTAX INTEGER {
        disable (0),
        enable (1)
    }
    MAX-ACCESS read-write
    STATUS current
    DESCRIPTION
     "The enable option for LLVD 3 function with high temperature."
    ::= { batteryManagementParameter 173 }
  -- 1.3.6.1.4.1.39553.10.3.5.174
    llvd4HighTempEnableOption OBJECT-TYPE
    SYNTAX INTEGER {
        disable (0),
        enable (1)
    }
    MAX-ACCESS read-write
    STATUS current
    DESCRIPTION
     "The enable option for LLVD 4 function with high temperature."
    ::= { batteryManagementParameter 174 }
  -- 1.3.6.1.4.1.39553.10.3.5.175
    llvd5HighTempEnableOption OBJECT-TYPE
    SYNTAX INTEGER {
        disable (0),
        enable (1)
    }
    MAX-ACCESS read-write
    STATUS current
    DESCRIPTION
     "The enable option for LLVD 5 function with high temperature."
    ::= { batteryManagementParameter 175 }
  -- 1.3.6.1.4.1.39553.10.3.5.176
    llvd6HighTempEnableOption OBJECT-TYPE
    SYNTAX INTEGER {
        disable (0),
        enable (1)
    }
    MAX-ACCESS read-write
    STATUS current
    DESCRIPTION
     "The enable option for LLVD 6 function with high temperature."
    ::= { batteryManagementParameter 176 }
  -- 1.3.6.1.4.1.39553.10.3.5.177
    llvd7HighTempEnableOption OBJECT-TYPE
    SYNTAX INTEGER {
        disable (0),
        enable (1)
    }
    MAX-ACCESS read-write
    STATUS current
    DESCRIPTION
     "The enable option for LLVD 6 function with high temperature."
    ::= { batteryManagementParameter 177 }
  -- 1.3.6.1.4.1.39553.10.3.5.178
    llvd8HighTempEnableOption OBJECT-TYPE
    SYNTAX INTEGER {
        disable (0),
        enable (1)
    }
    MAX-ACCESS read-write
    STATUS current
    DESCRIPTION
     "The enable option for LLVD 7 function with high temperature."
    ::= { batteryManagementParameter 178 }
  -- 1.3.6.1.4.1.39553.10.3.5.179
    llvd1HighTemp OBJECT-TYPE
    SYNTAX INTEGER
    MAX-ACCESS read-write
    STATUS current
    DESCRIPTION
     "The high temperature as a condition for LLVD 1 function.
      The actual value = the receive data/100.
      The unit of actual value is degree centigrade.
      Temperature range:The minimum value between 30 degree centigrade with Reconnect Low Temperature+4 .. 66 degree centigrade."
    ::= { batteryManagementParameter 179 }
  -- 1.3.6.1.4.1.39553.10.3.5.180
    llvd2HighTemp OBJECT-TYPE
    SYNTAX INTEGER
    MAX-ACCESS read-write
    STATUS current
    DESCRIPTION
     "The high temperature as a condition for LLVD 2 function.
      The actual value = the receive data/100.
      The unit of actual value is degree centigrade.
      Temperature range:The minimum value between 30 degree centigrade with Reconnect Low Temperature+4 .. 66 degree centigrade."
    ::= { batteryManagementParameter 180 }
  -- 1.3.6.1.4.1.39553.10.3.5.181
    llvd3HighTemp OBJECT-TYPE
    SYNTAX INTEGER
    MAX-ACCESS read-write
    STATUS current
    DESCRIPTION
     "The high temperature as a condition for LLVD 3 function.
      The actual value = the receive data/100.
      The unit of actual value is degree centigrade.
      Temperature range:The minimum value between 30 degree centigrade with Reconnect Low Temperature+4 .. 66 degree centigrade."
    ::= { batteryManagementParameter 181 }
  -- 1.3.6.1.4.1.39553.10.3.5.182
    llvd4HighTemp OBJECT-TYPE
    SYNTAX INTEGER
    MAX-ACCESS read-write
    STATUS current
    DESCRIPTION
     "The high temperature as a condition for LLVD 4 function.
      The actual value = the receive data/100.
      The unit of actual value is degree centigrade.
      Temperature range:The minimum value between 30 degree centigrade with Reconnect Low Temperature+4 .. 66 degree centigrade."
    ::= { batteryManagementParameter 182 }
  -- 1.3.6.1.4.1.39553.10.3.5.183
    llvd5HighTemp OBJECT-TYPE
    SYNTAX INTEGER
    MAX-ACCESS read-write
    STATUS current
    DESCRIPTION
     "The high temperature as a condition for LLVD 5 function.
      The actual value = the receive data/100.
      The unit of actual value is degree centigrade.
      Temperature range:The minimum value between 30 degree centigrade with Reconnect Low Temperature+4 .. 66 degree centigrade."
    ::= { batteryManagementParameter 183 }
  -- 1.3.6.1.4.1.39553.10.3.5.184
    llvd6HighTemp OBJECT-TYPE
    SYNTAX INTEGER
    MAX-ACCESS read-write
    STATUS current
    DESCRIPTION
     "The high temperature as a condition for LLVD 6 function.
      The actual value = the receive data/100.
      The unit of actual value is degree centigrade.
      Temperature range:The minimum value between 30 degree centigrade with Reconnect Low Temperature+4 .. 66 degree centigrade."
    ::= { batteryManagementParameter 184 }
  -- 1.3.6.1.4.1.39553.10.3.5.185
    llvd7HighTemp OBJECT-TYPE
    SYNTAX INTEGER
    MAX-ACCESS read-write
    STATUS current
    DESCRIPTION
     "The high temperature as a condition for LLVD 7 function.
      The actual value = the receive data/100.
      The unit of actual value is degree centigrade.
      Temperature range:The minimum value between 30 degree centigrade with Reconnect Low Temperature+4 .. 66 degree centigrade."
    ::= { batteryManagementParameter 185 }
  -- 1.3.6.1.4.1.39553.10.3.5.186
    llvd8HighTemp OBJECT-TYPE
    SYNTAX INTEGER
    MAX-ACCESS read-write
    STATUS current
    DESCRIPTION
     "The high temperature as a condition for LLVD 8 function.
      The actual value = the receive data/100.
      The unit of actual value is degree centigrade.
      Temperature range:The minimum value between 30 degree centigrade with Reconnect Low Temperature+4 .. 66 degree centigrade."
    ::= { batteryManagementParameter 186 }
  -- 1.3.6.1.4.1.39553.10.3.5.187
    llvd1HighTempReconnect OBJECT-TYPE
    SYNTAX INTEGER
    MAX-ACCESS read-write
    STATUS current
    DESCRIPTION
     "The high temperature as a condition for LLVD 1 reconnect function.
      The actual value = the receive data/100.
      The unit of actual value is degree centigrade.
      Temperature range:26 degree centigrade .. The maximum value between 62 degree centigrade and Disconnect High Temperature-4."
    ::= { batteryManagementParameter 187 }
  -- 1.3.6.1.4.1.39553.10.3.5.188
    llvd2HighTempReconnect OBJECT-TYPE
    SYNTAX INTEGER
    MAX-ACCESS read-write
    STATUS current
    DESCRIPTION
     "The high temperature as a condition for LLVD 2 reconnect function.
      The actual value = the receive data/100.
      The unit of actual value is degree centigrade.
      Temperature range:26 degree centigrade .. The maximum value between 62 degree centigrade and Disconnect High Temperature-4."
    ::= { batteryManagementParameter 188 }
  -- 1.3.6.1.4.1.39553.10.3.5.189
    llvd3HighTempReconnect OBJECT-TYPE
    SYNTAX INTEGER
    MAX-ACCESS read-write
    STATUS current
    DESCRIPTION
     "The high temperature as a condition for LLVD 3 reconnect function.
      The actual value = the receive data/100.
      The unit of actual value is degree centigrade.
      Temperature range:26 degree centigrade .. The maximum value between 62 degree centigrade and Disconnect High Temperature-4."
    ::= { batteryManagementParameter 189 }
  -- 1.3.6.1.4.1.39553.10.3.5.190
    llvd4HighTempReconnect OBJECT-TYPE
    SYNTAX INTEGER
    MAX-ACCESS read-write
    STATUS current
    DESCRIPTION
     "The high temperature as a condition for LLVD 4 reconnect function.
      The actual value = the receive data/100.
      The unit of actual value is degree centigrade.
      Temperature range:26 degree centigrade .. The maximum value between 62 degree centigrade and Disconnect High Temperature-4."
    ::= { batteryManagementParameter 190 }
  -- 1.3.6.1.4.1.39553.10.3.5.191
    llvd5HighTempReconnect OBJECT-TYPE
    SYNTAX INTEGER
    MAX-ACCESS read-write
    STATUS current
    DESCRIPTION
     "The high temperature as a condition for LLVD 5 reconnect function.
      The actual value = the receive data/100.
      The unit of actual value is degree centigrade.
      Temperature range:26 degree centigrade .. The maximum value between 62 degree centigrade and Disconnect High Temperature-4."
    ::= { batteryManagementParameter 191 }
  -- 1.3.6.1.4.1.39553.10.3.5.192
    llvd6HighTempReconnect OBJECT-TYPE
    SYNTAX INTEGER
    MAX-ACCESS read-write
    STATUS current
    DESCRIPTION
     "The high temperature as a condition for LLVD 6 reconnect function.
      The actual value = the receive data/100.
      The unit of actual value is degree centigrade.
      Temperature range:26 degree centigrade .. The maximum value between 62 degree centigrade and Disconnect High Temperature-4."
    ::= { batteryManagementParameter 192 }
  -- 1.3.6.1.4.1.39553.10.3.5.193
    llvd7HighTempReconnect OBJECT-TYPE
    SYNTAX INTEGER
    MAX-ACCESS read-write
    STATUS current
    DESCRIPTION
     "The high temperature as a condition for LLVD 7 reconnect function.
      The actual value = the receive data/100.
      The unit of actual value is degree centigrade.
      Temperature range:26 degree centigrade .. The maximum value between 62 degree centigrade and Disconnect High Temperature-4."
    ::= { batteryManagementParameter 193 }
  -- 1.3.6.1.4.1.39553.10.3.5.194
    llvd8HighTempReconnect OBJECT-TYPE
    SYNTAX INTEGER
    MAX-ACCESS read-write
    STATUS current
    DESCRIPTION
     "The high temperature as a condition for LLVD 8 reconnect function.
      The actual value = the receive data/100.
      The unit of actual value is degree centigrade.
      Temperature range:26 degree centigrade .. The maximum value between 62 degree centigrade and Disconnect High Temperature-4."
    ::= { batteryManagementParameter 194 }
  -- 1.3.6.1.4.1.39553.10.3.5.195
    llvd1LowTempEnableOption OBJECT-TYPE
    SYNTAX INTEGER {
        disable (0),
        enable (1)
    }
    MAX-ACCESS read-write
    STATUS current
    DESCRIPTION
     "The enable option for LLVD 1 function with low temperature."
    ::= { batteryManagementParameter 195 }
  -- 1.3.6.1.4.1.39553.10.3.5.196
    llvd2LowTempEnableOption OBJECT-TYPE
    SYNTAX INTEGER {
        disable (0),
        enable (1)
    }
    MAX-ACCESS read-write
    STATUS current
    DESCRIPTION
     "The enable option for LLVD 2 function with low temperature."
    ::= { batteryManagementParameter 196 }
  -- 1.3.6.1.4.1.39553.10.3.5.197
    llvd3LowTempEnableOption OBJECT-TYPE
    SYNTAX INTEGER {
        disable (0),
        enable (1)
    }
    MAX-ACCESS read-write
    STATUS current
    DESCRIPTION
     "The enable option for LLVD 3 function with low temperature."
    ::= { batteryManagementParameter 197 }
  -- 1.3.6.1.4.1.39553.10.3.5.198
    llvd4LowTempEnableOption OBJECT-TYPE
    SYNTAX INTEGER {
        disable (0),
        enable (1)
    }
    MAX-ACCESS read-write
    STATUS current
    DESCRIPTION
     "The enable option for LLVD 4 function with low temperature."
    ::= { batteryManagementParameter 198 }
  -- 1.3.6.1.4.1.39553.10.3.5.199
    llvd5LowTempEnableOption OBJECT-TYPE
    SYNTAX INTEGER {
        disable (0),
        enable (1)
    }
    MAX-ACCESS read-write
    STATUS current
    DESCRIPTION
     "The enable option for LLVD 5 function with low temperature."
    ::= { batteryManagementParameter 199 }
  -- 1.3.6.1.4.1.39553.10.3.5.200
    llvd6LowTempEnableOption OBJECT-TYPE
    SYNTAX INTEGER {
        disable (0),
        enable (1)
    }
    MAX-ACCESS read-write
    STATUS current
    DESCRIPTION
     "The enable option for LLVD 6 function with low temperature."
    ::= { batteryManagementParameter 200 }
  -- 1.3.6.1.4.1.39553.10.3.5.201
    llvd7LowTempEnableOption OBJECT-TYPE
    SYNTAX INTEGER {
        disable (0),
        enable (1)
    }
    MAX-ACCESS read-write
    STATUS current
    DESCRIPTION
     "The enable option for LLVD 7 function with low temperature."
    ::= { batteryManagementParameter 201 }
  -- 1.3.6.1.4.1.39553.10.3.5.202
    llvd8LowTempEnableOption OBJECT-TYPE
    SYNTAX INTEGER {
        disable (0),
        enable (1)
    }
    MAX-ACCESS read-write
    STATUS current
    DESCRIPTION
     "The enable option for LLVD 8 function with low temperature."
    ::= { batteryManagementParameter 202 }
  -- 1.3.6.1.4.1.39553.10.3.5.203
    llvd1LowTemp OBJECT-TYPE
    SYNTAX INTEGER
    MAX-ACCESS read-write
    STATUS current
    DESCRIPTION
     "The low temperature as a condition for LLVD 1 function.
      The actual value = the receive data/100.
      The unit of actual value is degree centigrade.
      Temperature range:The maximum value between 16 degree centigrade with Reconnect Low Temperature-4 .. -33 degree centigrade."
    ::= { batteryManagementParameter 203 }
  -- 1.3.6.1.4.1.39553.10.3.5.204
    llvd2LowTemp OBJECT-TYPE
    SYNTAX INTEGER
    MAX-ACCESS read-write
    STATUS current
    DESCRIPTION
     "The low temperature as a condition for LLVD 2 function.
      The actual value = the receive data/100.
      The unit of actual value is degree centigrade.
      Temperature range:The maximum value between 16 degree centigrade with Reconnect Low Temperature-4 .. -33 degree centigrade."
    ::= { batteryManagementParameter 204 }
  -- 1.3.6.1.4.1.39553.10.3.5.205
    llvd3LowTemp OBJECT-TYPE
    SYNTAX INTEGER
    MAX-ACCESS read-write
    STATUS current
    DESCRIPTION
     "The low temperature as a condition for LLVD 3 function.
      The actual value = the receive data/100.
      The unit of actual value is degree centigrade.
      Temperature range:The maximum value between 16 degree centigrade with Reconnect Low Temperature-4 .. -33 degree centigrade."
    ::= { batteryManagementParameter 205 }
  -- 1.3.6.1.4.1.39553.10.3.5.206
    llvd4LowTemp OBJECT-TYPE
    SYNTAX INTEGER
    MAX-ACCESS read-write
    STATUS current
    DESCRIPTION
     "The low temperature as a condition for LLVD 4 function.
      The actual value = the receive data/100.
      The unit of actual value is degree centigrade.
      Temperature range:The maximum value between 16 degree centigrade with Reconnect Low Temperature-4 .. -33 degree centigrade."
    ::= { batteryManagementParameter 206 }
  -- 1.3.6.1.4.1.39553.10.3.5.207
    llvd5LowTemp OBJECT-TYPE
    SYNTAX INTEGER
    MAX-ACCESS read-write
    STATUS current
    DESCRIPTION
     "The low temperature as a condition for LLVD 5 function.
      The actual value = the receive data/100.
      The unit of actual value is degree centigrade.
      Temperature range:The maximum value between 16 degree centigrade with Reconnect Low Temperature-4 .. -33 degree centigrade."
    ::= { batteryManagementParameter 207 }
  -- 1.3.6.1.4.1.39553.10.3.5.208
    llvd6LowTemp OBJECT-TYPE
    SYNTAX INTEGER
    MAX-ACCESS read-write
    STATUS current
    DESCRIPTION
     "The low temperature as a condition for LLVD 6 function.
      The actual value = the receive data/100.
      The unit of actual value is degree centigrade.
      Temperature range:The maximum value between 16 degree centigrade with Reconnect Low Temperature-4 .. -33 degree centigrade."
    ::= { batteryManagementParameter 208 }
  -- 1.3.6.1.4.1.39553.10.3.5.209
    llvd7LowTemp OBJECT-TYPE
    SYNTAX INTEGER
    MAX-ACCESS read-write
    STATUS current
    DESCRIPTION
     "The low temperature as a condition for LLVD 7 function.
      The actual value = the receive data/100.
      The unit of actual value is degree centigrade.
      Temperature range:The maximum value between 16 degree centigrade with Reconnect Low Temperature-4 .. -33 degree centigrade."
    ::= { batteryManagementParameter 209 }
  -- 1.3.6.1.4.1.39553.10.3.5.210
    llvd8LowTemp OBJECT-TYPE
    SYNTAX INTEGER
    MAX-ACCESS read-write
    STATUS current
    DESCRIPTION
     "The low temperature as a condition for LLVD 8 function.
      The actual value = the receive data/100.
      The unit of actual value is degree centigrade.
      Temperature range:The maximum value between 16 degree centigrade with Reconnect Low Temperature-4 .. -33 degree centigrade."
    ::= { batteryManagementParameter 210 }
  -- 1.3.6.1.4.1.39553.10.3.5.211
    llvd1LowTempReconnect OBJECT-TYPE
    SYNTAX INTEGER
    MAX-ACCESS read-write
    STATUS current
    DESCRIPTION
     "The low temperature as a condition for LLVD 1 reconnect function.
      The actual value = the receive data/100.
      The unit of actual value is degree centigrade.
      Temperature range:The minimum value between -29 degree centigrade and Disconnect Low Temperature +4 .. 20 degree centigrade."
    ::= { batteryManagementParameter 211 }
  -- 1.3.6.1.4.1.39553.10.3.5.212
    llvd2LowTempReconnect OBJECT-TYPE
    SYNTAX INTEGER
    MAX-ACCESS read-write
    STATUS current
    DESCRIPTION
     "The low temperature as a condition for LLVD 2 reconnect function.
      The actual value = the receive data/100.
      The unit of actual value is degree centigrade.
      Temperature range:The minimum value between -29 degree centigrade and Disconnect Low Temperature +4 .. 20 degree centigrade."
    ::= { batteryManagementParameter 212 }
  -- 1.3.6.1.4.1.39553.10.3.5.213
    llvd3LowTempReconnect OBJECT-TYPE
    SYNTAX INTEGER
    MAX-ACCESS read-write
    STATUS current
    DESCRIPTION
     "The low temperature as a condition for LLVD 3 reconnect function.
      The actual value = the receive data/100.
      The unit of actual value is degree centigrade.
      Temperature range:The minimum value between -29 degree centigrade and Disconnect Low Temperature +4 .. 20 degree centigrade."
    ::= { batteryManagementParameter 213 }
  -- 1.3.6.1.4.1.39553.10.3.5.214
    llvd4LowTempReconnect OBJECT-TYPE
    SYNTAX INTEGER
    MAX-ACCESS read-write
    STATUS current
    DESCRIPTION
     "The low temperature as a condition for LLVD 4 reconnect function.
      The actual value = the receive data/100.
      The unit of actual value is degree centigrade.
      Temperature range:The minimum value between -29 degree centigrade and Disconnect Low Temperature +4 .. 20 degree centigrade."
    ::= { batteryManagementParameter 214 }
  -- 1.3.6.1.4.1.39553.10.3.5.215
    llvd5LowTempReconnect OBJECT-TYPE
    SYNTAX INTEGER
    MAX-ACCESS read-write
    STATUS current
    DESCRIPTION
     "The low temperature as a condition for LLVD 5 reconnect function.
      The actual value = the receive data/100.
      The unit of actual value is degree centigrade.
      Temperature range:The minimum value between -29 degree centigrade and Disconnect Low Temperature +4 .. 20 degree centigrade."
    ::= { batteryManagementParameter 215 }
  -- 1.3.6.1.4.1.39553.10.3.5.216
    llvd6LowTempReconnect OBJECT-TYPE
    SYNTAX INTEGER
    MAX-ACCESS read-write
    STATUS current
    DESCRIPTION
     "The low temperature as a condition for LLVD 6 reconnect function.
      The actual value = the receive data/100.
      The unit of actual value is degree centigrade.
      Temperature range:The minimum value between -29 degree centigrade and Disconnect Low Temperature +4 .. 20 degree centigrade."
    ::= { batteryManagementParameter 216 }
  -- 1.3.6.1.4.1.39553.10.3.5.217
    llvd7LowTempReconnect OBJECT-TYPE
    SYNTAX INTEGER
    MAX-ACCESS read-write
    STATUS current
    DESCRIPTION
     "The low temperature as a condition for LLVD 7 reconnect function.
      The actual value = the receive data/100.
      The unit of actual value is degree centigrade.
      Temperature range:The minimum value between -29 degree centigrade and Disconnect Low Temperature +4 .. 20 degree centigrade."
    ::= { batteryManagementParameter 217 }
  -- 1.3.6.1.4.1.39553.10.3.5.218
    llvd8LowTempReconnect OBJECT-TYPE
    SYNTAX INTEGER
    MAX-ACCESS read-write
    STATUS current
    DESCRIPTION
     "The low temperature as a condition for LLVD 8 reconnect function.
      The actual value = the receive data/100.
      The unit of actual value is degree centigrade.
      Temperature range:The minimum value between -29 degree centigrade and Disconnect Low Temperature +4 .. 20 degree centigrade."
    ::= { batteryManagementParameter 218 }
  -- 1.3.6.1.4.1.39553.10.3.5.219
    llvd1DelayTime OBJECT-TYPE
    SYNTAX INTEGER(0..900)
    MAX-ACCESS read-write
    STATUS current
    DESCRIPTION
     "The delay time for LLVD 1 function.
      The actual value = the receive data.
      The unit of actual value is second.
      Delay time range:0 .. 900s."
    ::= { batteryManagementParameter 219 }
  -- 1.3.6.1.4.1.39553.10.3.5.220
    llvd2DelayTime OBJECT-TYPE
    SYNTAX INTEGER(0..900)
    MAX-ACCESS read-write
    STATUS current
    DESCRIPTION
     "The delay time for LLVD 2 function.
      The actual value = the receive data.
      The unit of actual value is second.
      Delay time range:0 .. 900s."
    ::= { batteryManagementParameter 220 }
  -- 1.3.6.1.4.1.39553.10.3.5.221
    llvd3DelayTime OBJECT-TYPE
    SYNTAX INTEGER(0..900)
    MAX-ACCESS read-write
    STATUS current
    DESCRIPTION
     "The delay time for LLVD 3 function.
      The actual value = the receive data.
      The unit of actual value is second.
      Delay time range:0 .. 900s."
    ::= { batteryManagementParameter 221 }
  -- 1.3.6.1.4.1.39553.10.3.5.222
    llvd4DelayTime OBJECT-TYPE
    SYNTAX INTEGER(0..900)
    MAX-ACCESS read-write
    STATUS current
    DESCRIPTION
     "The delay time for LLVD 4 function.
      The actual value = the receive data.
      The unit of actual value is second.
      Delay time range:0 .. 900s."
    ::= { batteryManagementParameter 222 }
  -- 1.3.6.1.4.1.39553.10.3.5.223
    llvd5DelayTime OBJECT-TYPE
    SYNTAX INTEGER(0..900)
    MAX-ACCESS read-write
    STATUS current
    DESCRIPTION
     "The delay time for LLVD 5 function.
      The actual value = the receive data.
      The unit of actual value is second.
      Delay time range:0 .. 900s."
    ::= { batteryManagementParameter 223 }
  -- 1.3.6.1.4.1.39553.10.3.5.224
    llvd6DelayTime OBJECT-TYPE
    SYNTAX INTEGER(0..900)
    MAX-ACCESS read-write
    STATUS current
    DESCRIPTION
     "The delay time for LLVD 6 function.
      The actual value = the receive data.
      The unit of actual value is second.
      Delay time range:0 .. 900s."
    ::= { batteryManagementParameter 224 }
  -- 1.3.6.1.4.1.39553.10.3.5.225
    llvd7DelayTime OBJECT-TYPE
    SYNTAX INTEGER(0..900)
    MAX-ACCESS read-write
    STATUS current
    DESCRIPTION
     "The delay time for LLVD 7 function.
      The actual value = the receive data.
      The unit of actual value is second.
      Delay time range:0 .. 900s."
    ::= { batteryManagementParameter 225 }
  -- 1.3.6.1.4.1.39553.10.3.5.226
    llvd8DelayTime OBJECT-TYPE
    SYNTAX INTEGER(0..900)
    MAX-ACCESS read-write
    STATUS current
    DESCRIPTION
     "The delay time for LLVD 8 function.
      The actual value = the receive data.
      The unit of actual value is second.
      Delay time range:0 .. 900s."
    ::= { batteryManagementParameter 226 }
  -- 1.3.6.1.4.1.39553.10.3.5.227
    blvdDelayTime OBJECT-TYPE
    SYNTAX INTEGER(0..900)
    MAX-ACCESS read-write
    STATUS current
    DESCRIPTION
     "The delay time for BLVD function.
      The actual value = the receive data.
      The unit of actual value is second.
      Delay time range:0 .. 900s."
    ::= { batteryManagementParameter 227 }
  -- 1.3.6.1.4.1.39553.10.3.5.228
    blvdHighTempReconnect OBJECT-TYPE
    SYNTAX INTEGER
    MAX-ACCESS read-write
    STATUS current
    DESCRIPTION
     "The high temperature as a condition for BLVD reconnect function.
      The actual value = the receive data/100.
      The unit of actual value is degree centigrade.
      Temperature range:26 degree centigrade .. The maximum value between 62 degree centigrade and Disconnect High Temperature-4."
    ::= { batteryManagementParameter 228 }
  -- 1.3.6.1.4.1.39553.10.3.5.229
    blvdLowTempReconnect OBJECT-TYPE
    SYNTAX INTEGER
    MAX-ACCESS read-write
    STATUS current
    DESCRIPTION
     "The low temperature as a condition for BLVD reconnect function.
      The actual value = the receive data/100.
      The unit of actual value is degree centigrade.
      Temperature range:The minimum value between -29 degree centigrade and Disconnect Low Temperature +4 .. 20 degree centigrade."
    ::= { batteryManagementParameter 229 }
  -- 1.3.6.1.4.1.39553.10.3.5.230
    llvd1TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 1."
    ::= { batteryManagementParameter 230 }
  -- 1.3.6.1.4.1.39553.10.3.5.231
    llvd2TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 2."
    ::= { batteryManagementParameter 231 }
  -- 1.3.6.1.4.1.39553.10.3.5.232
    llvd3TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 3."
    ::= { batteryManagementParameter 232 }
  -- 1.3.6.1.4.1.39553.10.3.5.233
    llvd4TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 4."
    ::= { batteryManagementParameter 233 }
  -- 1.3.6.1.4.1.39553.10.3.5.234
    llvd5TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 5."
    ::= { batteryManagementParameter 234 }
  -- 1.3.6.1.4.1.39553.10.3.5.235
    llvd6TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 6."
    ::= { batteryManagementParameter 235 }
  -- 1.3.6.1.4.1.39553.10.3.5.236
    llvd7TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 7."
    ::= { batteryManagementParameter 236 }
  -- 1.3.6.1.4.1.39553.10.3.5.237
    llvd8TempSensorSelect OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for LLVD 8."
    ::= { batteryManagementParameter 237 }
  -- 1.3.6.1.4.1.39553.10.3.5.238
    blvdTempSensorSelect1 OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for BLVD with temperature."
    ::= { batteryManagementParameter 238 }
    -- 1.3.6.1.4.1.39553.10.3.5.239
    blvdTempSensorSelect2 OBJECT-TYPE
    SYNTAX INTEGER {
        none (0),
        temperature1 (1),
        temperature2 (2),
        ex1Temperature1 (3),
        ex1Temperature2 (4),
        ex1humidityTempSensor (5),
        ex2Temperature1 (6),
        ex2Temperature2 (7),
        ex2humidityTempSensor (8),
        ex3Temperature1 (9),
        ex3Temperature2 (10),
        ex3humidityTempSensor (11),
        ex4Temperature1 (12),
        ex4Temperature2 (13),
        ex4humidityTempSensor (14),
        ex5Temperature1 (15),
        ex5Temperature2 (16),
        ex5humidityTempSensor (17)
    }
    MAX-ACCESS read-write
    STATUS current
    DESCRIPTION
     "Select temperature sensor for BLVD with temperature."
    ::= { batteryManagementParameter 239 }
    -- 1.3.6.1.4.1.39553.10.3.5.240
    btrmSensorSelect OBJECT-TYPE
    SYNTAX INTEGER{
        none (0),
        battery1Temperature (1),
        battery2Temperature (2),
        battery3Temperature (3),
        battery4Temperature (4),
        battery5Temperature (5),
        battery6Temperature (6),
        battery7Temperature (7),
        battery8Temperature (8),
        maximumTemperature (10),
        averageTemperature (11)
    }
    MAX-ACCESS read-write
    STATUS current
    DESCRIPTION
     "Select temperature sensor for BTRM with temperature."
    ::= { batteryManagementParameter 240 }
    -- 1.3.6.1.4.1.39553.10.3.5.241
    batteryTempCompensateSensor OBJECT-TYPE
    SYNTAX INTEGER{
        none (0),
        battery1Temperature (1),
        battery2Temperature (2),
        battery3Temperature (3),
        battery4Temperature (4),
        battery5Temperature (5),
        battery6Temperature (6),
        battery7Temperature (7),
        battery8Temperature (8),
        maximumTemperature (10),
        averageTemperature (11)
    }
    MAX-ACCESS read-write
    STATUS current
    DESCRIPTION
     "Select temperature sensor for battery temperature compensate."
    ::= { batteryManagementParameter 241 }
    -- 1.3.6.1.4.1.39553.10.3.5.242
    btrmVoltageSet OBJECT-TYPE
    SYNTAX INTEGER
    MAX-ACCESS read-write
    STATUS current
    DESCRIPTION
     "The voltage as a condition for BTRM function.
      The actual value = the receive data/100.
      The unit of actual value is V.
      Voltage range:30V .. Float Voltage."
    ::= { batteryManagementParameter 242 }
    -- 1.3.6.1.4.1.39553.10.3.5.243
    emergencyVoltage OBJECT-TYPE
    SYNTAX INTEGER(3000..6000)
    MAX-ACCESS read-write
    STATUS current
    DESCRIPTION
     "The rectifier emergency voltage for system.
      The actual value = the receive data/100.
      The unit of actual value is V.
      Voltage range:30V .. 60V."
    ::= { batteryManagementParameter 243 }  
    -- 1.3.6.1.4.1.39553.10.3.5.244
    batteryPredictionChargeEnable OBJECT-TYPE
    SYNTAX INTEGER{
        disable (0),
        enable (1)
    }
    MAX-ACCESS read-write
    STATUS current
    DESCRIPTION
     "Prediction charge enable."
    ::= { batteryManagementParameter 244 }
    -- 1.3.6.1.4.1.39553.10.3.5.245
    batteryPredictionChargeCurrent OBJECT-TYPE
    SYNTAX INTEGER(30..100)
    MAX-ACCESS read-write
    STATUS current
    DESCRIPTION
     "Battery prediction charge current.
      The actual value = the receive data/1000.
      The unit of actual value is C10.
      Current range:0.03C10 .. 0.1C10."
    ::= { batteryManagementParameter 245 }  
    -- 1.3.6.1.4.1.39553.10.3.5.246
    batteryPredictionChargeEndVoltage OBJECT-TYPE
    SYNTAX INTEGER(3000..4800)
    MAX-ACCESS read-write
    STATUS current
    DESCRIPTION
     "Battery prediction charge end voltage.
      The actual value = the receive data/100.
      The unit of actual value is V.
      range:30V .. 48V and float voltage."
    ::= { batteryManagementParameter 246 }  
    -- 1.3.6.1.4.1.39553.10.3.5.247
    batteryPredictionChargeTime OBJECT-TYPE
    SYNTAX INTEGER(100..6000)
    MAX-ACCESS read-write
    STATUS current
    DESCRIPTION
     "Battery prediction charge time.
      The actual value = the receive data/100.
      The unit of actual value is minute.
      range:1min .. 60min."
    ::= { batteryManagementParameter 247 }  
    -- 1.3.6.1.4.1.39553.10.3.5.248
    moduleLostQuitBoostEnable OBJECT-TYPE
    SYNTAX INTEGER{
        disable (0),
        enable (1)
    }
    MAX-ACCESS read-write
    STATUS current
    DESCRIPTION
     "Quit boost charge when module lost enable."
    ::= { batteryManagementParameter 248 }
    -- 1.3.6.1.4.1.39553.10.3.5.249
    moudleLostQuitTCompeEnable OBJECT-TYPE
    SYNTAX INTEGER{
        disable (0),
        enable (1)
    }
    MAX-ACCESS read-write
    STATUS current
    DESCRIPTION
     "Quit temperature compensation when module lost enable."
    ::= { batteryManagementParameter 249 }
    -- 1.3.6.1.4.1.39553.10.3.5.250
    batteryFullChargeLimitCurrent OBJECT-TYPE
    SYNTAX INTEGER{
        disable (0),
        enable (1)
    }
    MAX-ACCESS read-write
    STATUS current
    DESCRIPTION
     "Limit current when battery full charge."
    ::= { batteryManagementParameter 250 }
    -- 1.3.6.1.4.1.39553.10.3.5.251
    batteryFuseBreakOverCurrentProtection OBJECT-TYPE
    SYNTAX INTEGER{
        disable (0),
        enable (1)
    }
    MAX-ACCESS read-write
    STATUS current
    DESCRIPTION
     "Protect battery from over current when battery fuse break."
    ::= { batteryManagementParameter 251 }
    -- 1.3.6.1.4.1.39553.10.3.5.252
    busVoltageRiseSpeed OBJECT-TYPE
    SYNTAX INTEGER(2000..5000000)
    MAX-ACCESS read-write
    STATUS current
    DESCRIPTION
     "Bus Voltage Rise Speed.
      The actual value = the receive data/100.
      The unit of actual value is mV.
      range:20mV .. 50000mV."
    ::= { batteryManagementParameter 252 }  
    -- 1.3.6.1.4.1.39553.10.3.5.253
    batteryCapacityPrediction OBJECT-TYPE
    SYNTAX INTEGER{
        disable (0),
        enable (1)
    }
    MAX-ACCESS read-write
    STATUS current
    DESCRIPTION
     "Battery Capacity Prediction."
    ::= { batteryManagementParameter 253 }
    -- 1.3.6.1.4.1.39553.10.3.5.254
    batteryDischargeThreshold OBJECT-TYPE
    SYNTAX INTEGER(0..500)
    MAX-ACCESS read-write
    STATUS current
    DESCRIPTION
     "Current threshold to judge if battery is in discharge state.
      The actual value = the receive data/100.
      The unit of actual value is %.
      range:-0.5 .. batteryDischargeRecoveryThreshold."
    ::= { batteryManagementParameter 254 }  
    -- 1.3.6.1.4.1.39553.10.3.5.255
    batteryDischargeRecoveryThreshold OBJECT-TYPE
    SYNTAX INTEGER(0..500)
    MAX-ACCESS read-write
    STATUS current
    DESCRIPTION
     "Current threshold to judge if battery is in charge state.
      The actual value = the receive data/100.
      The unit of actual value is %.
      range:batteryDischargeThreshold .. 5%."
    ::= { batteryManagementParameter 255 }  
    -- 1.3.6.1.4.1.39553.10.3.5.256
    battery1CurrentLimit OBJECT-TYPE
	SYNTAX INTEGER(100..2000)
	MAX-ACCESS read-write
	STATUS current
	DESCRIPTION
	 "Charge current limit of battery 1.
	  The actual value = the receive data/1000.
	  The unit of actual value is C10.
	  range:0.1 .. 2C10."
	::= { batteryManagementParameter 256 }	
	
	-- 1.3.6.1.4.1.39553.10.3.5.257
	battery2CurrentLimit OBJECT-TYPE
	SYNTAX INTEGER(100..2000)
	MAX-ACCESS read-write
	STATUS current
	DESCRIPTION
	 "Charge current limit of battery 2.
	  The actual value = the receive data/1000.
	  The unit of actual value is C10.
	  range:0.1 .. 2C10."
	::= { batteryManagementParameter 257 }
	
	-- 1.3.6.1.4.1.39553.10.3.5.258
	battery3CurrentLimit OBJECT-TYPE
	SYNTAX INTEGER(100..2000)
	MAX-ACCESS read-write
	STATUS current
	DESCRIPTION
	 "Charge current limit of battery 3.
	  The actual value = the receive data/1000.
	  The unit of actual value is C10.
	  range:0.1 .. 2C10."
	::= { batteryManagementParameter 258 }	
	
	-- 1.3.6.1.4.1.39553.10.3.5.259
	battery4CurrentLimit OBJECT-TYPE
	SYNTAX INTEGER(100..2000)
	MAX-ACCESS read-write
	STATUS current
	DESCRIPTION
	 "Charge current limit of battery 4.
	  The actual value = the receive data/1000.
	  The unit of actual value is C10.
	  range:0.1 .. 2C10."
	::= { batteryManagementParameter 259 }	
	
	-- 1.3.6.1.4.1.39553.10.3.5.260
	battery5CurrentLimit OBJECT-TYPE
	SYNTAX INTEGER(100..2000)
	MAX-ACCESS read-write
	STATUS current
	DESCRIPTION
	 "Charge current limit of battery 5.
	  The actual value = the receive data/1000.
	  The unit of actual value is C10.
	  range:0.1 .. 2C10."
	::= { batteryManagementParameter 260 }	
	
	-- 1.3.6.1.4.1.39553.10.3.5.261
	battery6CurrentLimit OBJECT-TYPE
	SYNTAX INTEGER(100..2000)
	MAX-ACCESS read-write
	STATUS current
	DESCRIPTION
	 "Charge current limit of battery 6.
	  The actual value = the receive data/1000.
	  The unit of actual value is C10.
	  range:0.1 .. 2C10."
	::= { batteryManagementParameter 261 }	
	
	-- 1.3.6.1.4.1.39553.10.3.5.262
	battery7CurrentLimit OBJECT-TYPE
	SYNTAX INTEGER(100..2000)
	MAX-ACCESS read-write
	STATUS current
	DESCRIPTION
	 "Charge current limit of battery 7.
	  The actual value = the receive data/1000.
	  The unit of actual value is C10.
	  range:0.1 .. 2C10."
	::= { batteryManagementParameter 262 }	
	
	-- 1.3.6.1.4.1.39553.10.3.5.263
	battery8CurrentLimit OBJECT-TYPE
	SYNTAX INTEGER(100..2000)
	MAX-ACCESS read-write
	STATUS current
	DESCRIPTION
	 "Charge current limit of battery 8.
	  The actual value = the receive data/1000.
	  The unit of actual value is C10.
	  range:0.1 .. 2C10."
	::= { batteryManagementParameter 263 }	
	-- 1.3.6.1.4.1.39553.10.3.5.264
	batteriesUseIndependentCurrentLimitFactor OBJECT-TYPE
	SYNTAX INTEGER{
		disable (0),
		enable (1)
	}
	MAX-ACCESS read-write
	STATUS current
	DESCRIPTION
	 "Batteries use independent current limit factor."
	::= { batteryManagementParameter 264 }

------------------------------------------------------------
-- System Control{ dcDistribution 6 }
------------------------------------------------------------    
  -- 1.3.6.1.4.1.39553.10.3.6
    systemControl OBJECT IDENTIFIER ::= { dcDistribution 6 }    

  -- 1.3.6.1.4.1.39553.10.3.6.1
    manualToBoost OBJECT-TYPE
    SYNTAX INTEGER {
        no (0),
        yes (1)
    }
    MAX-ACCESS read-write
    STATUS current
    DESCRIPTION 
        "The enable for the manual to boost funtion."
    ::= { systemControl 1 }
  -- 1.3.6.1.4.1.39553.10.3.6.2
    manualToFloat OBJECT-TYPE
    SYNTAX INTEGER {
        no (0),
        yes (1)
    }
    MAX-ACCESS read-write
    STATUS current
    DESCRIPTION 
        "The enable for the manual to float funtion."
    ::= { systemControl 2 }
  -- 1.3.6.1.4.1.39553.10.3.6.3
    manualLLVDAll OBJECT-TYPE
    SYNTAX INTEGER {
        disconnect (0),
        connect (1)
    }
    MAX-ACCESS read-write
    STATUS current
    DESCRIPTION 
        "Control all the system's LLVD connect or disconnect in manual mode."
    ::= { systemControl 3 }
  -- 1.3.6.1.4.1.39553.10.3.6.4
    manualLLVD1 OBJECT-TYPE
    SYNTAX INTEGER {
        disconnect (0),
        connect (1)
    }
    MAX-ACCESS read-write
    STATUS current
    DESCRIPTION 
        "Control the system's LLVD 1 connect or disconnect in manual mode."
    ::= { systemControl 4 }
  -- 1.3.6.1.4.1.39553.10.3.6.5
    manualLLVD2 OBJECT-TYPE
    SYNTAX INTEGER {
        disconnect (0),
        connect (1)
    }
    MAX-ACCESS read-write
    STATUS current
    DESCRIPTION 
        "Control the system's LLVD 2 connect or disconnect in manual mode."
    ::= { systemControl 5 }
  -- 1.3.6.1.4.1.39553.10.3.6.6
    manualLLVD3 OBJECT-TYPE
    SYNTAX INTEGER {
        disconnect (0),
        connect (1)
    }
    MAX-ACCESS read-write
    STATUS current
    DESCRIPTION 
        "Control the system's LLVD 3 connect or disconnect in manual mode."
    ::= { systemControl 6 }
  -- 1.3.6.1.4.1.39553.10.3.6.7
    manualLLVD4 OBJECT-TYPE
    SYNTAX INTEGER {
        disconnect (0),
        connect (1)
    }
    MAX-ACCESS read-write
    STATUS current
    DESCRIPTION 
        "Control the system's LLVD 4 connect or disconnect in manual mode."
    ::= { systemControl 7 }
  -- 1.3.6.1.4.1.39553.10.3.6.8
    manualLLVD5 OBJECT-TYPE
    SYNTAX INTEGER {
        disconnect (0),
        connect (1)
    }
    MAX-ACCESS read-write
    STATUS current
    DESCRIPTION 
        "Control the system's LLVD 5 connect or disconnect in manual mode."
    ::= { systemControl 8 }
  -- 1.3.6.1.4.1.39553.10.3.6.9
    manualLLVD6 OBJECT-TYPE
    SYNTAX INTEGER {
        disconnect (0),
        connect (1)
    }
    MAX-ACCESS read-write
    STATUS current
    DESCRIPTION 
        "Control the system's LLVD 6 connect or disconnect in manual mode."
    ::= { systemControl 9 }
  -- 1.3.6.1.4.1.39553.10.3.6.10
    manualLLVD7 OBJECT-TYPE
    SYNTAX INTEGER {
        disconnect (0),
        connect (1)
    }
    MAX-ACCESS read-write
    STATUS current
    DESCRIPTION 
        "Control the system's LLVD 7 connect or disconnect in manual mode."
    ::= { systemControl 10 }
  -- 1.3.6.1.4.1.39553.10.3.6.11
    manualLLVD8 OBJECT-TYPE
    SYNTAX INTEGER {
        disconnect (0),
        connect (1)
    }
    MAX-ACCESS read-write
    STATUS current
    DESCRIPTION 
        "Control the system's LLVD 8 connect or disconnect in manual mode."
    ::= { systemControl 11 }
  -- 1.3.6.1.4.1.39553.10.3.6.12
    manualBLVD OBJECT-TYPE
    SYNTAX INTEGER {
        disconnect (0),
        connect (1)
    }
    MAX-ACCESS read-write
    STATUS current
    DESCRIPTION 
        "Control the system's BLVD connect or disconnect in manual mode."
    ::= { systemControl 12 }
  -- 1.3.6.1.4.1.39553.10.3.6.13
    energySaveFunctionEnable OBJECT-TYPE
    SYNTAX INTEGER {
        disable (0),
        enable (1)
    }
    MAX-ACCESS read-write
    STATUS current
    DESCRIPTION 
        "The enable for the power save function."
    ::= { systemControl 13 }
  -- 1.3.6.1.4.1.39553.10.3.6.14
    minimumRectifierNumECO OBJECT-TYPE
    SYNTAX INTEGER (0..128)
    MAX-ACCESS read-write
    STATUS current
    DESCRIPTION 
        "The minimum rectifier number for ECO function."
    ::= { systemControl 14 }
  -- 1.3.6.1.4.1.39553.10.3.6.15
    rectifierOnOffPeriodECO OBJECT-TYPE
    SYNTAX INTEGER (1..72000)
    MAX-ACCESS read-write
    STATUS current
    DESCRIPTION 
        "The period for control on or off the rectifier for ECO function.
         The actual value = The set or receive data / 100.
         The unit of actual value is hour."
    ::= { systemControl 15 }
  -- 1.3.6.1.4.1.39553.10.3.6.16
    rectifierPowerOnLoadRate OBJECT-TYPE
    SYNTAX INTEGER (10000..95000)
    MAX-ACCESS read-write
    STATUS current
    DESCRIPTION 
        "The load rate for control power on the rectifier for ECO function.
         The actual value = The set or receive data / 1000.
         The unit of actual value is %."
    ::= { systemControl 16 }
  -- 1.3.6.1.4.1.39553.10.3.6.17
    rectifierPowerOffLoadRate OBJECT-TYPE
    SYNTAX INTEGER (0..85000)
    MAX-ACCESS read-write
    STATUS current
    DESCRIPTION 
        "The load rate for control power off the rectifier for ECO function.
         The actual value = The set or receive data / 1000.
         The unit of actual value is %."
    ::= { systemControl 17 }
  -- 1.3.6.1.4.1.39553.10.3.6.18
    ecoEnableWithoutBattery OBJECT-TYPE
    SYNTAX INTEGER {
        disable (0),
        enable (1)
    }
    MAX-ACCESS read-write
    STATUS current
    DESCRIPTION 
        "System without battery if enable the ECO function."
    ::= { systemControl 18 }
  -- 1.3.6.1.4.1.39553.10.3.6.19
    ecoStatus OBJECT-TYPE
    SYNTAX INTEGER {
        halt (0),
        running (1)
    }
    MAX-ACCESS read-only
    STATUS current
    DESCRIPTION 
       "The status of the ECO."
    ::= { systemControl 19 }
  -- 1.3.6.1.4.1.39553.10.3.6.20
    currentLoadRate OBJECT-TYPE
    SYNTAX INTEGER (0..100000)
    MAX-ACCESS read-only
    STATUS current
    DESCRIPTION 
        "The load rate for rectifier.
         The actual value = The set or receive data / 1000.
         The unit of actual value is %."
    ::= { systemControl 20 }
        
    

    
    
------------------------------------------------------------
-- DC Parameter { dcDistribution 8 }
------------------------------------------------------------
-- 1.3.6.1.4.1.39553.10.3.8
    dcParameter OBJECT IDENTIFIER ::= { dcDistribution 8 }  
        
  -- 1.3.6.1.4.1.39553.10.3.8.1
    loadBranchCurrentNumber OBJECT-TYPE
    SYNTAX INTEGER (0..72)
    MAX-ACCESS read-write
    STATUS current
    DESCRIPTION 
        "The number of branch for load current in the system."
    ::= { dcParameter 1 }
  -- 1.3.6.1.4.1.39553.10.3.8.2
    loadBranchStatusNumber OBJECT-TYPE
    SYNTAX INTEGER (0..72)
    MAX-ACCESS read-write
    STATUS current
    DESCRIPTION 
        "The number of branch for load status in the system."
    ::= { dcParameter 2 }
  -- 1.3.6.1.4.1.39553.10.3.8.3
    llvdNumber OBJECT-TYPE
    SYNTAX INTEGER (0..7)
    MAX-ACCESS read-write
    STATUS current
    DESCRIPTION 
        "The number of LLVD in the system."
    ::= { dcParameter 3 }
  -- 1.3.6.1.4.1.39553.10.3.8.4
    sc210Number OBJECT-TYPE
    SYNTAX INTEGER (0..2)
    MAX-ACCESS read-write
    STATUS current
    DESCRIPTION 
        "The number of SC210 in the system which is for slave controller."
    ::= { dcParameter 4 }
  -- 1.3.6.1.4.1.39553.10.3.8.5
    sc320Number OBJECT-TYPE
    SYNTAX INTEGER (0..5)
    MAX-ACCESS read-write
    STATUS current
    DESCRIPTION 
        "The number of SC320 in the system which for DI and DO extend unit."
    ::= { dcParameter 5 }
  -- 1.3.6.1.4.1.39553.10.3.8.6
    sc340Number OBJECT-TYPE
    SYNTAX INTEGER (0..3)
    MAX-ACCESS read-write
    STATUS current
    DESCRIPTION 
        "The number of SC340 in the system which is for detection branch status."
    ::= { dcParameter 6 }
  -- 1.3.6.1.4.1.39553.10.3.8.7
    sc910Number OBJECT-TYPE
    SYNTAX INTEGER (0..2)
    MAX-ACCESS read-write
    STATUS current
    DESCRIPTION 
        "The number of SC910 in the system which is for AC meter function."
    ::= { dcParameter 7 }
  -- 1.3.6.1.4.1.39553.10.3.8.8
    sc930Number OBJECT-TYPE
    SYNTAX INTEGER (0..2)
    MAX-ACCESS read-write
    STATUS current
    DESCRIPTION 
        "The number of SC930 in the system which is for AC ATS function."
    ::= { dcParameter 8 }
  -- 1.3.6.1.4.1.39553.10.3.8.9
    sc501Number OBJECT-TYPE
    SYNTAX INTEGER (0..2)
    MAX-ACCESS read-write
    STATUS current
    DESCRIPTION 
        "The number of SC501 in the system which is main controller."
    ::= { dcParameter 9 }
  -- 1.3.6.1.4.1.39553.10.3.8.10
    sc310Number OBJECT-TYPE
    SYNTAX INTEGER (0..3)
    MAX-ACCESS read-write
    STATUS current
    DESCRIPTION 
        "The number of SC310 in the system which is for detection branch current."
    ::= { dcParameter 10 }
  -- 1.3.6.1.4.1.39553.10.3.8.11
    sc200Number OBJECT-TYPE
    SYNTAX INTEGER (0..2)
    MAX-ACCESS read-write
    STATUS current
    DESCRIPTION 
        "The number of SC200 in the system which is dc distribution controller."
    ::= { dcParameter 11 }
  -- 1.3.6.1.4.1.39553.10.3.8.12
    sc900Number OBJECT-TYPE
    SYNTAX INTEGER (0..1)
    MAX-ACCESS read-write
    STATUS current
    DESCRIPTION 
        "The number of SC900 in the system which is AC controller."
    ::= { dcParameter 12 }
  -- 1.3.6.1.4.1.39553.10.3.8.13        
    dcLoadBranch1CurrentRating OBJECT-TYPE  
    SYNTAX INTEGER (25..2000)   
    MAX-ACCESS read-write   
    STATUS current  
    DESCRIPTION     
        "The dc load branch 1 current rating. The unit is A."
    ::= { dcParameter 13 }  
  -- 1.3.6.1.4.1.39553.10.3.8.14        
    dcLoadBranch2CurrentRating OBJECT-TYPE  
    SYNTAX INTEGER (25..2000)   
    MAX-ACCESS read-write   
    STATUS current  
    DESCRIPTION     
        "The dc load branch 2 current rating. The unit is A."
    ::= { dcParameter 14 }  
  -- 1.3.6.1.4.1.39553.10.3.8.15        
    dcLoadBranch3CurrentRating OBJECT-TYPE  
    SYNTAX INTEGER (25..2000)   
    MAX-ACCESS read-write   
    STATUS current  
    DESCRIPTION     
        "The dc load branch 3 current rating. The unit is A."
    ::= { dcParameter 15 }  
  -- 1.3.6.1.4.1.39553.10.3.8.16        
    dcLoadBranch4CurrentRating OBJECT-TYPE  
    SYNTAX INTEGER (25..2000)   
    MAX-ACCESS read-write   
    STATUS current  
    DESCRIPTION     
        "The dc load branch 4 current rating. The unit is A."
    ::= { dcParameter 16 }  
  -- 1.3.6.1.4.1.39553.10.3.8.17        
    dcLoadBranch5CurrentRating OBJECT-TYPE  
    SYNTAX INTEGER (25..2000)   
    MAX-ACCESS read-write   
    STATUS current  
    DESCRIPTION     
        "The dc load branch 5 current rating. The unit is A."
    ::= { dcParameter 17 }  
  -- 1.3.6.1.4.1.39553.10.3.8.18        
    dcLoadBranch6CurrentRating OBJECT-TYPE  
    SYNTAX INTEGER (25..2000)   
    MAX-ACCESS read-write   
    STATUS current  
    DESCRIPTION     
        "The dc load branch 6 current rating. The unit is A."
    ::= { dcParameter 18 }  
  -- 1.3.6.1.4.1.39553.10.3.8.19        
    dcLoadBranch7CurrentRating OBJECT-TYPE  
    SYNTAX INTEGER (25..2000)   
    MAX-ACCESS read-write   
    STATUS current  
    DESCRIPTION     
        "The dc load branch 7 current rating. The unit is A."
    ::= { dcParameter 19 }  
  -- 1.3.6.1.4.1.39553.10.3.8.20        
    dcLoadBranch8CurrentRating OBJECT-TYPE  
    SYNTAX INTEGER (25..2000)   
    MAX-ACCESS read-write   
    STATUS current  
    DESCRIPTION     
        "The dc load branch 8 current rating. The unit is A."
    ::= { dcParameter 20 }  
  -- 1.3.6.1.4.1.39553.10.3.8.21        
    dcLoadBranch9CurrentRating OBJECT-TYPE  
    SYNTAX INTEGER (25..2000)   
    MAX-ACCESS read-write   
    STATUS current  
    DESCRIPTION     
        "The dc load branch 9 current rating. The unit is A."
    ::= { dcParameter 21 }  
  -- 1.3.6.1.4.1.39553.10.3.8.22        
    dcLoadBranch10CurrentRating OBJECT-TYPE 
    SYNTAX INTEGER (25..2000)   
    MAX-ACCESS read-write   
    STATUS current  
    DESCRIPTION     
        "The dc load branch 10 current rating. The unit is A."
    ::= { dcParameter 22 }  
  -- 1.3.6.1.4.1.39553.10.3.8.23        
    dcLoadBranch11CurrentRating OBJECT-TYPE 
    SYNTAX INTEGER (25..2000)   
    MAX-ACCESS read-write   
    STATUS current  
    DESCRIPTION     
        "The dc load branch 11 current rating. The unit is A."
    ::= { dcParameter 23 }  
  -- 1.3.6.1.4.1.39553.10.3.8.24        
    dcLoadBranch12CurrentRating OBJECT-TYPE 
    SYNTAX INTEGER (25..2000)   
    MAX-ACCESS read-write   
    STATUS current  
    DESCRIPTION     
        "The dc load branch 12 current rating. The unit is A."
    ::= { dcParameter 24 }  
  -- 1.3.6.1.4.1.39553.10.3.8.25        
    dcLoadBranch13CurrentRating OBJECT-TYPE 
    SYNTAX INTEGER (25..2000)   
    MAX-ACCESS read-write   
    STATUS current  
    DESCRIPTION     
        "The dc load branch 13 current rating. The unit is A."
    ::= { dcParameter 25 }  
  -- 1.3.6.1.4.1.39553.10.3.8.26        
    dcLoadBranch14CurrentRating OBJECT-TYPE 
    SYNTAX INTEGER (25..2000)   
    MAX-ACCESS read-write   
    STATUS current  
    DESCRIPTION     
        "The dc load branch 14 current rating. The unit is A."
    ::= { dcParameter 26 }  
  -- 1.3.6.1.4.1.39553.10.3.8.27        
    dcLoadBranch15CurrentRating OBJECT-TYPE 
    SYNTAX INTEGER (25..2000)   
    MAX-ACCESS read-write   
    STATUS current  
    DESCRIPTION     
        "The dc load branch 15 current rating. The unit is A."
    ::= { dcParameter 27 }  
  -- 1.3.6.1.4.1.39553.10.3.8.28        
    dcLoadBranch16CurrentRating OBJECT-TYPE 
    SYNTAX INTEGER (25..2000)   
    MAX-ACCESS read-write   
    STATUS current  
    DESCRIPTION     
        "The dc load branch 16 current rating. The unit is A."
    ::= { dcParameter 28 }  
  -- 1.3.6.1.4.1.39553.10.3.8.29        
    dcLoadBranch17CurrentRating OBJECT-TYPE 
    SYNTAX INTEGER (25..2000)   
    MAX-ACCESS read-write   
    STATUS current  
    DESCRIPTION     
        "The dc load branch 17 current rating. The unit is A."
    ::= { dcParameter 29 }  
  -- 1.3.6.1.4.1.39553.10.3.8.30        
    dcLoadBranch18CurrentRating OBJECT-TYPE 
    SYNTAX INTEGER (25..2000)   
    MAX-ACCESS read-write   
    STATUS current  
    DESCRIPTION     
        "The dc load branch 18 current rating. The unit is A."
    ::= { dcParameter 30 }  
  -- 1.3.6.1.4.1.39553.10.3.8.31        
    dcLoadBranch19CurrentRating OBJECT-TYPE 
    SYNTAX INTEGER (25..2000)   
    MAX-ACCESS read-write   
    STATUS current  
    DESCRIPTION     
        "The dc load branch 19 current rating. The unit is A."
    ::= { dcParameter 31 }  
  -- 1.3.6.1.4.1.39553.10.3.8.32        
    dcLoadBranch20CurrentRating OBJECT-TYPE 
    SYNTAX INTEGER (25..2000)   
    MAX-ACCESS read-write   
    STATUS current  
    DESCRIPTION     
        "The dc load branch 20 current rating. The unit is A."
    ::= { dcParameter 32 }  
  -- 1.3.6.1.4.1.39553.10.3.8.33        
    dcLoadBranch21CurrentRating OBJECT-TYPE 
    SYNTAX INTEGER (25..2000)   
    MAX-ACCESS read-write   
    STATUS current  
    DESCRIPTION     
        "The dc load branch 21 current rating. The unit is A."
    ::= { dcParameter 33 }  
  -- 1.3.6.1.4.1.39553.10.3.8.34        
    dcLoadBranch22CurrentRating OBJECT-TYPE 
    SYNTAX INTEGER (25..2000)   
    MAX-ACCESS read-write   
    STATUS current  
    DESCRIPTION     
        "The dc load branch 22 current rating. The unit is A."
    ::= { dcParameter 34 }  
  -- 1.3.6.1.4.1.39553.10.3.8.35        
    dcLoadBranch23CurrentRating OBJECT-TYPE 
    SYNTAX INTEGER (25..2000)   
    MAX-ACCESS read-write   
    STATUS current  
    DESCRIPTION     
        "The dc load branch 23 current rating. The unit is A."
    ::= { dcParameter 35 }  
  -- 1.3.6.1.4.1.39553.10.3.8.36        
    dcLoadBranch24CurrentRating OBJECT-TYPE 
    SYNTAX INTEGER (25..2000)   
    MAX-ACCESS read-write   
    STATUS current  
    DESCRIPTION     
        "The dc load branch 24 current rating. The unit is A."
    ::= { dcParameter 36 }  
  -- 1.3.6.1.4.1.39553.10.3.8.37        
    dcLoadBranch25CurrentRating OBJECT-TYPE 
    SYNTAX INTEGER (25..2000)   
    MAX-ACCESS read-write   
    STATUS current  
    DESCRIPTION     
        "The dc load branch 25 current rating. The unit is A."
    ::= { dcParameter 37 }  
  -- 1.3.6.1.4.1.39553.10.3.8.38        
    dcLoadBranch26CurrentRating OBJECT-TYPE 
    SYNTAX INTEGER (25..2000)   
    MAX-ACCESS read-write   
    STATUS current  
    DESCRIPTION     
        "The dc load branch 26 current rating. The unit is A."
    ::= { dcParameter 38 }  
  -- 1.3.6.1.4.1.39553.10.3.8.39        
    dcLoadBranch27CurrentRating OBJECT-TYPE 
    SYNTAX INTEGER (25..2000)   
    MAX-ACCESS read-write   
    STATUS current  
    DESCRIPTION     
        "The dc load branch 27 current rating. The unit is A."
    ::= { dcParameter 39 }  
  -- 1.3.6.1.4.1.39553.10.3.8.40        
    dcLoadBranch28CurrentRating OBJECT-TYPE 
    SYNTAX INTEGER (25..2000)   
    MAX-ACCESS read-write   
    STATUS current  
    DESCRIPTION     
        "The dc load branch 28 current rating. The unit is A."
    ::= { dcParameter 40 }  
  -- 1.3.6.1.4.1.39553.10.3.8.41        
    dcLoadBranch29CurrentRating OBJECT-TYPE 
    SYNTAX INTEGER (25..2000)   
    MAX-ACCESS read-write   
    STATUS current  
    DESCRIPTION     
        "The dc load branch 29 current rating. The unit is A."
    ::= { dcParameter 41 }  
  -- 1.3.6.1.4.1.39553.10.3.8.42        
    dcLoadBranch30CurrentRating OBJECT-TYPE 
    SYNTAX INTEGER (25..2000)   
    MAX-ACCESS read-write   
    STATUS current  
    DESCRIPTION     
        "The dc load branch 30 current rating. The unit is A."
    ::= { dcParameter 42 }  
  -- 1.3.6.1.4.1.39553.10.3.8.43        
    dcLoadBranch31CurrentRating OBJECT-TYPE 
    SYNTAX INTEGER (25..2000)   
    MAX-ACCESS read-write   
    STATUS current  
    DESCRIPTION     
        "The dc load branch 31 current rating. The unit is A."
    ::= { dcParameter 43 }  
  -- 1.3.6.1.4.1.39553.10.3.8.44        
    dcLoadBranch32CurrentRating OBJECT-TYPE 
    SYNTAX INTEGER (25..2000)   
    MAX-ACCESS read-write   
    STATUS current  
    DESCRIPTION     
        "The dc load branch 32 current rating. The unit is A."
    ::= { dcParameter 44 }  
  -- 1.3.6.1.4.1.39553.10.3.8.45        
    dcLoadBranch33CurrentRating OBJECT-TYPE 
    SYNTAX INTEGER (25..2000)   
    MAX-ACCESS read-write   
    STATUS current  
    DESCRIPTION     
        "The dc load branch 33 current rating. The unit is A."
    ::= { dcParameter 45 }  
  -- 1.3.6.1.4.1.39553.10.3.8.46        
    dcLoadBranch34CurrentRating OBJECT-TYPE 
    SYNTAX INTEGER (25..2000)   
    MAX-ACCESS read-write   
    STATUS current  
    DESCRIPTION     
        "The dc load branch 34 current rating. The unit is A."
    ::= { dcParameter 46 }  
  -- 1.3.6.1.4.1.39553.10.3.8.47        
    dcLoadBranch35CurrentRating OBJECT-TYPE 
    SYNTAX INTEGER (25..2000)   
    MAX-ACCESS read-write   
    STATUS current  
    DESCRIPTION     
        "The dc load branch 35 current rating. The unit is A."
    ::= { dcParameter 47 }  
  -- 1.3.6.1.4.1.39553.10.3.8.48        
    dcLoadBranch36CurrentRating OBJECT-TYPE 
    SYNTAX INTEGER (25..2000)   
    MAX-ACCESS read-write   
    STATUS current  
    DESCRIPTION     
        "The dc load branch 36 current rating. The unit is A."
    ::= { dcParameter 48 }  
  -- 1.3.6.1.4.1.39553.10.3.8.49        
    dcLoadBranch37CurrentRating OBJECT-TYPE 
    SYNTAX INTEGER (25..2000)   
    MAX-ACCESS read-write   
    STATUS current  
    DESCRIPTION     
        "The dc load branch 37 current rating. The unit is A."
    ::= { dcParameter 49 }  
  -- 1.3.6.1.4.1.39553.10.3.8.50        
    dcLoadBranch38CurrentRating OBJECT-TYPE 
    SYNTAX INTEGER (25..2000)   
    MAX-ACCESS read-write   
    STATUS current  
    DESCRIPTION     
        "The dc load branch 38 current rating. The unit is A."
    ::= { dcParameter 50 }  
  -- 1.3.6.1.4.1.39553.10.3.8.51        
    dcLoadBranch39CurrentRating OBJECT-TYPE 
    SYNTAX INTEGER (25..2000)   
    MAX-ACCESS read-write   
    STATUS current  
    DESCRIPTION     
        "The dc load branch 39 current rating. The unit is A."
    ::= { dcParameter 51 }  
  -- 1.3.6.1.4.1.39553.10.3.8.52        
    dcLoadBranch40CurrentRating OBJECT-TYPE 
    SYNTAX INTEGER (25..2000)   
    MAX-ACCESS read-write   
    STATUS current  
    DESCRIPTION     
        "The dc load branch 40 current rating. The unit is A."
    ::= { dcParameter 52 }  
  -- 1.3.6.1.4.1.39553.10.3.8.53        
    dcLoadBranch41CurrentRating OBJECT-TYPE 
    SYNTAX INTEGER (25..2000)   
    MAX-ACCESS read-write   
    STATUS current  
    DESCRIPTION     
        "The dc load branch 41 current rating. The unit is A."
    ::= { dcParameter 53 }  
  -- 1.3.6.1.4.1.39553.10.3.8.54        
    dcLoadBranch42CurrentRating OBJECT-TYPE 
    SYNTAX INTEGER (25..2000)   
    MAX-ACCESS read-write   
    STATUS current  
    DESCRIPTION     
        "The dc load branch 42 current rating. The unit is A."
    ::= { dcParameter 54 }  
  -- 1.3.6.1.4.1.39553.10.3.8.55        
    dcLoadBranch43CurrentRating OBJECT-TYPE 
    SYNTAX INTEGER (25..2000)   
    MAX-ACCESS read-write   
    STATUS current  
    DESCRIPTION     
        "The dc load branch 43 current rating. The unit is A."
    ::= { dcParameter 55 }  
  -- 1.3.6.1.4.1.39553.10.3.8.56        
    dcLoadBranch44CurrentRating OBJECT-TYPE 
    SYNTAX INTEGER (25..2000)   
    MAX-ACCESS read-write   
    STATUS current  
    DESCRIPTION     
        "The dc load branch 44 current rating. The unit is A."
    ::= { dcParameter 56 }  
  -- 1.3.6.1.4.1.39553.10.3.8.57        
    dcLoadBranch45CurrentRating OBJECT-TYPE 
    SYNTAX INTEGER (25..2000)   
    MAX-ACCESS read-write   
    STATUS current  
    DESCRIPTION     
        "The dc load branch 45 current rating. The unit is A."
    ::= { dcParameter 57 }  
  -- 1.3.6.1.4.1.39553.10.3.8.58        
    dcLoadBranch46CurrentRating OBJECT-TYPE 
    SYNTAX INTEGER (25..2000)   
    MAX-ACCESS read-write   
    STATUS current  
    DESCRIPTION     
        "The dc load branch 46 current rating. The unit is A."
    ::= { dcParameter 58 }  
  -- 1.3.6.1.4.1.39553.10.3.8.59        
    dcLoadBranch47CurrentRating OBJECT-TYPE 
    SYNTAX INTEGER (25..2000)   
    MAX-ACCESS read-write   
    STATUS current  
    DESCRIPTION     
        "The dc load branch 47 current rating. The unit is A."
    ::= { dcParameter 59 }  
  -- 1.3.6.1.4.1.39553.10.3.8.60        
    dcLoadBranch48CurrentRating OBJECT-TYPE 
    SYNTAX INTEGER (25..2000)   
    MAX-ACCESS read-write   
    STATUS current  
    DESCRIPTION     
        "The dc load branch 48 current rating. The unit is A."
    ::= { dcParameter 60 }  
  -- 1.3.6.1.4.1.39553.10.3.8.61        
    dcLoadBranch49CurrentRating OBJECT-TYPE 
    SYNTAX INTEGER (25..2000)   
    MAX-ACCESS read-write   
    STATUS current  
    DESCRIPTION     
        "The dc load branch 49 current rating. The unit is A."
    ::= { dcParameter 61 }  
  -- 1.3.6.1.4.1.39553.10.3.8.62        
    dcLoadBranch50CurrentRating OBJECT-TYPE 
    SYNTAX INTEGER (25..2000)   
    MAX-ACCESS read-write   
    STATUS current  
    DESCRIPTION     
        "The dc load branch 50 current rating. The unit is A."
    ::= { dcParameter 62 }  
  -- 1.3.6.1.4.1.39553.10.3.8.63        
    dcLoadBranch51CurrentRating OBJECT-TYPE 
    SYNTAX INTEGER (25..2000)   
    MAX-ACCESS read-write   
    STATUS current  
    DESCRIPTION     
        "The dc load branch 51 current rating. The unit is A."
    ::= { dcParameter 63 }  
  -- 1.3.6.1.4.1.39553.10.3.8.64        
    dcLoadBranch52CurrentRating OBJECT-TYPE 
    SYNTAX INTEGER (25..2000)   
    MAX-ACCESS read-write   
    STATUS current  
    DESCRIPTION     
        "The dc load branch 52 current rating. The unit is A."
    ::= { dcParameter 64 }  
  -- 1.3.6.1.4.1.39553.10.3.8.65        
    dcLoadBranch53CurrentRating OBJECT-TYPE 
    SYNTAX INTEGER (25..2000)   
    MAX-ACCESS read-write   
    STATUS current  
    DESCRIPTION     
        "The dc load branch 53 current rating. The unit is A."
    ::= { dcParameter 65 }  
  -- 1.3.6.1.4.1.39553.10.3.8.66        
    dcLoadBranch54CurrentRating OBJECT-TYPE 
    SYNTAX INTEGER (25..2000)   
    MAX-ACCESS read-write   
    STATUS current  
    DESCRIPTION     
        "The dc load branch 54 current rating. The unit is A."
    ::= { dcParameter 66 }  
  -- 1.3.6.1.4.1.39553.10.3.8.67        
    dcLoadBranch55CurrentRating OBJECT-TYPE 
    SYNTAX INTEGER (25..2000)   
    MAX-ACCESS read-write   
    STATUS current  
    DESCRIPTION     
        "The dc load branch 55 current rating. The unit is A."
    ::= { dcParameter 67 }  
  -- 1.3.6.1.4.1.39553.10.3.8.68        
    dcLoadBranch56CurrentRating OBJECT-TYPE 
    SYNTAX INTEGER (25..2000)   
    MAX-ACCESS read-write   
    STATUS current  
    DESCRIPTION     
        "The dc load branch 56 current rating. The unit is A."
    ::= { dcParameter 68 }  
  -- 1.3.6.1.4.1.39553.10.3.8.69        
    dcLoadBranch57CurrentRating OBJECT-TYPE 
    SYNTAX INTEGER (25..2000)   
    MAX-ACCESS read-write   
    STATUS current  
    DESCRIPTION     
        "The dc load branch 57 current rating. The unit is A."
    ::= { dcParameter 69 }  
  -- 1.3.6.1.4.1.39553.10.3.8.70        
    dcLoadBranch58CurrentRating OBJECT-TYPE 
    SYNTAX INTEGER (25..2000)   
    MAX-ACCESS read-write   
    STATUS current  
    DESCRIPTION     
        "The dc load branch 58 current rating. The unit is A."
    ::= { dcParameter 70 }  
  -- 1.3.6.1.4.1.39553.10.3.8.71        
    dcLoadBranch59CurrentRating OBJECT-TYPE 
    SYNTAX INTEGER (25..2000)   
    MAX-ACCESS read-write   
    STATUS current  
    DESCRIPTION     
        "The dc load branch 59 current rating. The unit is A."
    ::= { dcParameter 71 }  
  -- 1.3.6.1.4.1.39553.10.3.8.72        
    dcLoadBranch60CurrentRating OBJECT-TYPE 
    SYNTAX INTEGER (25..2000)   
    MAX-ACCESS read-write   
    STATUS current  
    DESCRIPTION     
        "The dc load branch 60 current rating. The unit is A."
    ::= { dcParameter 72 }  
  -- 1.3.6.1.4.1.39553.10.3.8.73        
    dcLoadBranch61CurrentRating OBJECT-TYPE 
    SYNTAX INTEGER (25..2000)   
    MAX-ACCESS read-write   
    STATUS current  
    DESCRIPTION     
        "The dc load branch 61 current rating. The unit is A."
    ::= { dcParameter 73 }  
  -- 1.3.6.1.4.1.39553.10.3.8.74        
    dcLoadBranch62CurrentRating OBJECT-TYPE 
    SYNTAX INTEGER (25..2000)   
    MAX-ACCESS read-write   
    STATUS current  
    DESCRIPTION     
        "The dc load branch 62 current rating. The unit is A."
    ::= { dcParameter 74 }  
  -- 1.3.6.1.4.1.39553.10.3.8.75        
    dcLoadBranch63CurrentRating OBJECT-TYPE 
    SYNTAX INTEGER (25..2000)   
    MAX-ACCESS read-write   
    STATUS current  
    DESCRIPTION     
        "The dc load branch 63 current rating. The unit is A."
    ::= { dcParameter 75 }  
  -- 1.3.6.1.4.1.39553.10.3.8.76        
    dcLoadBranch64CurrentRating OBJECT-TYPE 
    SYNTAX INTEGER (25..2000)   
    MAX-ACCESS read-write   
    STATUS current  
    DESCRIPTION     
        "The dc load branch 64 current rating. The unit is A."
    ::= { dcParameter 76 }  
  -- 1.3.6.1.4.1.39553.10.3.8.77        
    dcLoadBranch65CurrentRating OBJECT-TYPE 
    SYNTAX INTEGER (25..2000)   
    MAX-ACCESS read-write   
    STATUS current  
    DESCRIPTION     
        "The dc load branch 65 current rating. The unit is A."
    ::= { dcParameter 77 }  
  -- 1.3.6.1.4.1.39553.10.3.8.78        
    dcLoadBranch66CurrentRating OBJECT-TYPE 
    SYNTAX INTEGER (25..2000)   
    MAX-ACCESS read-write   
    STATUS current  
    DESCRIPTION     
        "The dc load branch 66 current rating. The unit is A."
    ::= { dcParameter 78 }  
  -- 1.3.6.1.4.1.39553.10.3.8.79        
    dcLoadBranch67CurrentRating OBJECT-TYPE 
    SYNTAX INTEGER (25..2000)   
    MAX-ACCESS read-write   
    STATUS current  
    DESCRIPTION     
        "The dc load branch 67 current rating. The unit is A."
    ::= { dcParameter 79 }  
  -- 1.3.6.1.4.1.39553.10.3.8.80        
    dcLoadBranch68CurrentRating OBJECT-TYPE 
    SYNTAX INTEGER (25..2000)   
    MAX-ACCESS read-write   
    STATUS current  
    DESCRIPTION     
        "The dc load branch 68 current rating. The unit is A."
    ::= { dcParameter 80 }  
  -- 1.3.6.1.4.1.39553.10.3.8.81        
    dcLoadBranch69CurrentRating OBJECT-TYPE 
    SYNTAX INTEGER (25..2000)   
    MAX-ACCESS read-write   
    STATUS current  
    DESCRIPTION     
        "The dc load branch 69 current rating. The unit is A."
    ::= { dcParameter 81 }  
  -- 1.3.6.1.4.1.39553.10.3.8.82        
    dcLoadBranch70CurrentRating OBJECT-TYPE 
    SYNTAX INTEGER (25..2000)   
    MAX-ACCESS read-write   
    STATUS current  
    DESCRIPTION     
        "The dc load branch 70 current rating. The unit is A."
    ::= { dcParameter 82 }  
  -- 1.3.6.1.4.1.39553.10.3.8.83        
    dcLoadBranch71CurrentRating OBJECT-TYPE 
    SYNTAX INTEGER (25..2000)   
    MAX-ACCESS read-write   
    STATUS current  
    DESCRIPTION     
        "The dc load branch 71 current rating. The unit is A."
    ::= { dcParameter 83 }  
  -- 1.3.6.1.4.1.39553.10.3.8.84        
    dcLoadBranch72CurrentRating OBJECT-TYPE 
    SYNTAX INTEGER (25..2000)   
    MAX-ACCESS read-write   
    STATUS current  
    DESCRIPTION     
        "The dc load branch 72 current rating. The unit is A."
    ::= { dcParameter 84 }  
  -- 1.3.6.1.4.1.39553.10.3.8.85
    bmsNumber OBJECT-TYPE
    SYNTAX INTEGER (0..20)
    MAX-ACCESS read-write
    STATUS current
    DESCRIPTION 
        "The number of BMS in the system."
    ::= { dcParameter 85 }
  -- 1.3.6.1.4.1.39553.10.3.8.86
    --bmmNumber OBJECT-TYPE
    --SYNTAX INTEGER (0..10)
    --MAX-ACCESS read-write
    --STATUS current
    --DESCRIPTION 
        --"The number of BMM in the system."
    --::= { dcParameter 86 }  
  -- 1.3.6.1.4.1.39553.10.3.8.87
    cellNumber OBJECT-TYPE
    SYNTAX INTEGER (0..240)
    MAX-ACCESS read-write
    STATUS current
    DESCRIPTION 
        "The number of cells in the system."
    ::= { dcParameter 87 }
  -- 1.3.6.1.4.1.39553.10.3.8.88
    totalLoadCurrentMeasurementThreshold OBJECT-TYPE
    SYNTAX INTEGER (0..5000)
    UNITS   "%; i.e. 500 = 0.5%"
    MAX-ACCESS read-write
    STATUS current
    DESCRIPTION 
        "Total Load Current Measurement Threshold.
        UNITS %; i.e. 500 = 0.5%
        "
    ::= { dcParameter 88 }
  -- 1.3.6.1.4.1.39553.10.3.8.89
    batteryCurrentMeasurementThreshold OBJECT-TYPE
    SYNTAX INTEGER (0..5000)
    UNITS   "%; i.e. 500 = 0.5%"
    MAX-ACCESS read-write
    STATUS current
    DESCRIPTION 
        "Battery Current Measurement Threshold.
        UNITS %; i.e. 500 = 0.5%
        "
    ::= { dcParameter 89 }
  -- 1.3.6.1.4.1.39553.10.3.8.90
    loadBranchCurrentMeasurementThreshold OBJECT-TYPE
    SYNTAX INTEGER (0..5000)
    UNITS   "%; i.e. 500 = 0.5%"
    MAX-ACCESS read-write
    STATUS current
    DESCRIPTION 
        "Load Branch Current Measurement Threshold.
        UNITS %; i.e. 500 = 0.5%
        "
    ::= { dcParameter 90 }
  -- 1.3.6.1.4.1.39553.10.3.8.91
    blvdBatteryDischargeCurrentThreshold OBJECT-TYPE
    SYNTAX INTEGER (0..5000)
    UNITS   "%; i.e. 500 = 0.5%"
    MAX-ACCESS read-write
    STATUS current
    DESCRIPTION 
        "BLVD Battery Discharge Current Threshold.
        UNITS %; i.e. 500 = 0.5%
        "
    ::= { dcParameter 91 }
  -- 1.3.6.1.4.1.39553.10.3.8.92
    llvd1BatteryDischargeCurrentThreshold OBJECT-TYPE
    SYNTAX INTEGER (0..5000)
    UNITS   "%; i.e. 500 = 0.5%"
    MAX-ACCESS read-write
    STATUS current
    DESCRIPTION 
        "LLVD1 Battery Discharge Current Threshold.
        UNITS %; i.e. 500 = 0.5%
        "
    ::= { dcParameter 92 }
  -- 1.3.6.1.4.1.39553.10.3.8.93
    llvd2BatteryDischargeCurrentThreshold OBJECT-TYPE
    SYNTAX INTEGER (0..5000)
    UNITS   "%; i.e. 500 = 0.5%"
    MAX-ACCESS read-write
    STATUS current
    DESCRIPTION 
        "LLVD2 Battery Discharge Current Threshold.
        UNITS %; i.e. 500 = 0.5%
        "
    ::= { dcParameter 93 }
  -- 1.3.6.1.4.1.39553.10.3.8.94
    llvd3BatteryDischargeCurrentThreshold OBJECT-TYPE
    SYNTAX INTEGER (0..5000)
    UNITS   "%; i.e. 500 = 0.5%"
    MAX-ACCESS read-write
    STATUS current
    DESCRIPTION 
        "LLVD3 Battery Discharge Current Threshold.
        UNITS %; i.e. 500 = 0.5%
        "
    ::= { dcParameter 94 }
  -- 1.3.6.1.4.1.39553.10.3.8.95
    llvd4BatteryDischargeCurrentThreshold OBJECT-TYPE
    SYNTAX INTEGER (0..5000)
    UNITS   "%; i.e. 500 = 0.5%"
    MAX-ACCESS read-write
    STATUS current
    DESCRIPTION 
        "LLVD4 Battery Discharge Current Threshold.
        UNITS %; i.e. 500 = 0.5%
        "
    ::= { dcParameter 95 }
  -- 1.3.6.1.4.1.39553.10.3.8.96
    llvd5BatteryDischargeCurrentThreshold OBJECT-TYPE
    SYNTAX INTEGER (0..5000)
    UNITS   "%; i.e. 500 = 0.5%"
    MAX-ACCESS read-write
    STATUS current
    DESCRIPTION 
        "LLVD5 Battery Discharge Current Threshold.
        UNITS %; i.e. 500 = 0.5%
        "
    ::= { dcParameter 96 }
  -- 1.3.6.1.4.1.39553.10.3.8.97
    llvd6BatteryDischargeCurrentThreshold OBJECT-TYPE
    SYNTAX INTEGER (0..5000)
    UNITS   "%; i.e. 500 = 0.5%"
    MAX-ACCESS read-write
    STATUS current
    DESCRIPTION 
        "LLVD6 Battery Discharge Current Threshold.
        UNITS %; i.e. 500 = 0.5%
        "
    ::= { dcParameter 97 }
  -- 1.3.6.1.4.1.39553.10.3.8.98
    llvd7BatteryDischargeCurrentThreshold OBJECT-TYPE
    SYNTAX INTEGER (0..5000)
    UNITS   "%; i.e. 500 = 0.5%"
    MAX-ACCESS read-write
    STATUS current
    DESCRIPTION 
        "LLVD7 Battery Discharge Current Threshold.
        UNITS %; i.e. 500 = 0.5%
        "
    ::= { dcParameter 98 }
  -- 1.3.6.1.4.1.39553.10.3.8.99
    llvd8BatteryDischargeCurrentThreshold OBJECT-TYPE
    SYNTAX INTEGER (0..5000)
    UNITS   "%; i.e. 500 = 0.5%"
    MAX-ACCESS read-write
    STATUS current
    DESCRIPTION 
        "LLVD8 Battery Discharge Current Threshold.
        UNITS %; i.e. 500 = 0.5%
        "
    ::= { dcParameter 99 }
  -- 1.3.6.1.4.1.39553.10.3.8.100
    --temperatureSensor1Configuration OBJECT-TYPE
    --SYNTAX INTEGER {
        --none (0),
        --ambient1 (1),
        --ambient2 (2),
        --ambient3 (3),
        --ambient4 (4),
        --ambient5 (5),
        --battery1 (6),
        --battery2 (7),
        --battery3 (8),
        --battery4 (9),
        --battery5 (10),
        --battery6 (11),
        --battery7 (12),
        --battery8 (13)
    --}
   -- MAX-ACCESS read-write
    --STATUS current
    --DESCRIPTION 
        --"The temperature sensor 1 configuration."
    --::= { dcParameter 100 }
  -- 1.3.6.1.4.1.39553.10.3.8.101
    temperatureSensor1Curve OBJECT-TYPE
    SYNTAX INTEGER {
        default (0),
        curve1 (1),
        curve2 (2)
    }
    MAX-ACCESS read-write
    STATUS current
    DESCRIPTION 
        "The temperature sensor 1 curve."
    ::= { dcParameter 101 }
  -- 1.3.6.1.4.1.39553.10.3.8.102
    --temperatureSensor2Configuration OBJECT-TYPE
    --SYNTAX INTEGER {
        --none (0),
        --ambient1 (1),
        --ambient2 (2),
        --ambient3 (3),
        --ambient4 (4),
        --ambient5 (5),
        --battery1 (6),
        --battery2 (7),
        --battery3 (8),
        --battery4 (9),
        --battery5 (10),
        --battery6 (11),
        --battery7 (12),
        --battery8 (13)
    --}
    --MAX-ACCESS read-write
    --STATUS current
    --DESCRIPTION 
        --"The temperature sensor 2 configuration."
    --::= { dcParameter 102 }
  -- 1.3.6.1.4.1.39553.10.3.8.103
    temperatureSensor2Curve OBJECT-TYPE
    SYNTAX INTEGER {
        default (0),
        curve1 (1),
        curve2 (2)
    }
    MAX-ACCESS read-write
    STATUS current
    DESCRIPTION 
        "The temperature sensor 2 curve."
    ::= { dcParameter 103 }
  -- 1.3.6.1.4.1.39553.10.3.8.104
    ex1TemperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX1-Temperature sensor 1 configuration."
    ::= { dcParameter 104 }
  -- 1.3.6.1.4.1.39553.10.3.8.105
    ex1TemperatureSensor1Curve OBJECT-TYPE
    SYNTAX INTEGER {
        default (0),
        curve1 (1),
        curve2 (2)
    }
    MAX-ACCESS read-write
    STATUS current
    DESCRIPTION 
        "The EX1-Temperature sensor 1 curve."
    ::= { dcParameter 105 }
  -- 1.3.6.1.4.1.39553.10.3.8.106
    ex1TemperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX1-Temperature sensor 2 configuration."
    ::= { dcParameter 106 }
  -- 1.3.6.1.4.1.39553.10.3.8.107
    ex1TemperatureSensor2Curve OBJECT-TYPE
    SYNTAX INTEGER {
        default (0),
        curve1 (1),
        curve2 (2)
    }
    MAX-ACCESS read-write
    STATUS current
    DESCRIPTION 
        "The EX1-Temperature sensor 2 curve."
    ::= { dcParameter 107 }
  -- 1.3.6.1.4.1.39553.10.3.8.108
    ex1HumitureTemperatureSensorConfiguration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX1-Humiture&Temperature sensor configuration."
    ::= { dcParameter 108 }
  -- 1.3.6.1.4.1.39553.10.3.8.109
    ex1HumitureTemperatureSensorType OBJECT-TYPE
    SYNTAX INTEGER {
        current (0),
        voltage (1),
        fuelSensorType1 (2),
        fuelSensorType2 (3)
    }
    MAX-ACCESS read-write
    STATUS current
    DESCRIPTION 
        "The EX1-Humiture&Temperature sensor type."
    ::= { dcParameter 109 }
  -- 1.3.6.1.4.1.39553.10.3.8.110
    ex2TemperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX2-Temperature sensor 1 configuration."
    ::= { dcParameter 110 }
  -- 1.3.6.1.4.1.39553.10.3.8.111
    ex2TemperatureSensor1Curve OBJECT-TYPE
    SYNTAX INTEGER {
        default (0),
        curve1 (1),
        curve2 (2)
    }
    MAX-ACCESS read-write
    STATUS current
    DESCRIPTION 
        "The EX2-Temperature sensor 1 curve."
    ::= { dcParameter 111 }
  -- 1.3.6.1.4.1.39553.10.3.8.112
    ex2TemperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX2-Temperature sensor 2 configuration."
    ::= { dcParameter 112 }
  -- 1.3.6.1.4.1.39553.10.3.8.113
    ex2TemperatureSensor2Curve OBJECT-TYPE
    SYNTAX INTEGER {
        default (0),
        curve1 (1),
        curve2 (2)
    }
    MAX-ACCESS read-write
    STATUS current
    DESCRIPTION 
        "The EX2-Temperature sensor 2 curve."
    ::= { dcParameter 113 }
  -- 1.3.6.1.4.1.39553.10.3.8.114
    ex2HumitureTemperatureSensorConfiguration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX2-Humiture&Temperature sensor configuration."
    ::= { dcParameter 114 }
  -- 1.3.6.1.4.1.39553.10.3.8.115
    ex2HumitureTemperatureSensorType OBJECT-TYPE
    SYNTAX INTEGER {
        current (0),
        voltage (1),
        fuelSensorType1 (2),
        fuelSensorType2 (3)
    }
    MAX-ACCESS read-write
    STATUS current
    DESCRIPTION 
        "The EX2-Humiture&Temperature sensor type."
    ::= { dcParameter 115 }
  -- 1.3.6.1.4.1.39553.10.3.8.116
    ex3TemperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX3-Temperature sensor 1 configuration."
    ::= { dcParameter 116 }
  -- 1.3.6.1.4.1.39553.10.3.8.117
    ex3TemperatureSensor1Curve OBJECT-TYPE
    SYNTAX INTEGER {
        default (0),
        curve1 (1),
        curve2 (2)
    }
    MAX-ACCESS read-write
    STATUS current
    DESCRIPTION 
        "The EX3-Temperature sensor 1 curve."
    ::= { dcParameter 117 }
  -- 1.3.6.1.4.1.39553.10.3.8.118
    ex3TemperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX3-Temperature sensor 2 configuration."
    ::= { dcParameter 118 }
  -- 1.3.6.1.4.1.39553.10.3.8.119
    ex3TemperatureSensor2Curve OBJECT-TYPE
    SYNTAX INTEGER {
        default (0),
        curve1 (1),
        curve2 (2)
    }
    MAX-ACCESS read-write
    STATUS current
    DESCRIPTION 
        "The EX3-Temperature sensor 2 curve."
    ::= { dcParameter 119 }
  -- 1.3.6.1.4.1.39553.10.3.8.120
    ex3HumitureTemperatureSensorConfiguration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX3-Humiture&Temperature sensor configuration."
    ::= { dcParameter 120 }
  -- 1.3.6.1.4.1.39553.10.3.8.121
    ex3HumitureTemperatureSensorType OBJECT-TYPE
    SYNTAX INTEGER {
        current (0),
        voltage (1),
        fuelSensorType1 (2),
        fuelSensorType2 (3)
    }
    MAX-ACCESS read-write
    STATUS current
    DESCRIPTION 
        "The EX3-Humiture&Temperature sensor type."
    ::= { dcParameter 121 }
  -- 1.3.6.1.4.1.39553.10.3.8.122
    ex4TemperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX4-Temperature sensor 1 configuration."
    ::= { dcParameter 122 }
  -- 1.3.6.1.4.1.39553.10.3.8.123
    ex4TemperatureSensor1Curve OBJECT-TYPE
    SYNTAX INTEGER {
        default (0),
        curve1 (1),
        curve2 (2)
    }
    MAX-ACCESS read-write
    STATUS current
    DESCRIPTION 
        "The EX4-Temperature sensor 1 curve."
    ::= { dcParameter 123 }
  -- 1.3.6.1.4.1.39553.10.3.8.124
    ex4TemperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX4-Temperature sensor 2 configuration."
    ::= { dcParameter 124 }
  -- 1.3.6.1.4.1.39553.10.3.8.125
    ex4TemperatureSensor2Curve OBJECT-TYPE
    SYNTAX INTEGER {
        default (0),
        curve1 (1),
        curve2 (2)
    }
    MAX-ACCESS read-write
    STATUS current
    DESCRIPTION 
        "The EX4-Temperature sensor 2 curve."
    ::= { dcParameter 125 }
  -- 1.3.6.1.4.1.39553.10.3.8.126
    ex4HumitureTemperatureSensorConfiguration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX4-Humiture&Temperature sensor configuration."
    ::= { dcParameter 126 }
  -- 1.3.6.1.4.1.39553.10.3.8.127
    ex4HumitureTemperatureSensorType OBJECT-TYPE
    SYNTAX INTEGER {
        current (0),
        voltage (1),
        fuelSensorType1 (2),
        fuelSensorType2 (3)
    }
    MAX-ACCESS read-write
    STATUS current
    DESCRIPTION 
        "The EX4-Humiture&Temperature sensor type."
    ::= { dcParameter 127 }
  -- 1.3.6.1.4.1.39553.10.3.8.128
    ex5TemperatureSensor1Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX5-Temperature sensor 1 configuration."
    ::= { dcParameter 128 }
  -- 1.3.6.1.4.1.39553.10.3.8.129
    ex5TemperatureSensor1Curve OBJECT-TYPE
    SYNTAX INTEGER {
        default (0),
        curve1 (1),
        curve2 (2)
    }
    MAX-ACCESS read-write
    STATUS current
    DESCRIPTION 
        "The EX5-Temperature sensor 1 curve."
    ::= { dcParameter 129 }
  -- 1.3.6.1.4.1.39553.10.3.8.130
    ex5TemperatureSensor2Configuration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX5-Temperature sensor 2 configuration."
    ::= { dcParameter 130 }
  -- 1.3.6.1.4.1.39553.10.3.8.131
    ex5TemperatureSensor2Curve OBJECT-TYPE
    SYNTAX INTEGER {
        default (0),
        curve1 (1),
        curve2 (2)
    }
    MAX-ACCESS read-write
    STATUS current
    DESCRIPTION 
        "The EX5-Temperature sensor 2 curve."
    ::= { dcParameter 131 }
  -- 1.3.6.1.4.1.39553.10.3.8.132
    ex5HumitureTemperatureSensorConfiguration OBJECT-TYPE
    SYNTAX INTEGER {
        none (0),
        ambient1 (1),
        ambient2 (2),
        ambient3 (3),
        ambient4 (4),
        ambient5 (5),
        battery1 (6),
        battery2 (7),
        battery3 (8),
        battery4 (9),
        battery5 (10),
        battery6 (11),
        battery7 (12),
        battery8 (13)
    }
    MAX-ACCESS read-write
    STATUS current
    DESCRIPTION 
        "The EX5-Humiture&Temperature sensor configuration."
    ::= { dcParameter 132 }
  -- 1.3.6.1.4.1.39553.10.3.8.133
    ex5HumitureTemperatureSensorType OBJECT-TYPE
    SYNTAX INTEGER {
        current (0),
        voltage (1),
        fuelSensorType1 (2),
        fuelSensorType2 (3)
    }
    MAX-ACCESS read-write
    STATUS current
    DESCRIPTION 
        "The EX5-Humiture&Temperature sensor type."
    ::= { dcParameter 133 }
  -- 1.3.6.1.4.1.39553.10.3.8.134
    ex1HumitureTemperatureSensorMinimumValue OBJECT-TYPE
    SYNTAX INTEGER (-4000..10000)
    MAX-ACCESS read-write
    STATUS current
    DESCRIPTION 
        "The lower limit for the EX1-Humiture Temperature sensor sample range.
        The actual value = The set or receive data / 100."
    ::= { dcParameter 134 }
  -- 1.3.6.1.4.1.39553.10.3.8.135
    ex1HumitureTemperatureSensorMaximumValue OBJECT-TYPE
    SYNTAX INTEGER (-4000..10000)
    MAX-ACCESS read-write
    STATUS current
    DESCRIPTION 
        "The upper limit for the EX1-Humiture Temperature sensor sample range.
        The actual value = The set or receive data / 100."
    ::= { dcParameter 135 }
  -- 1.3.6.1.4.1.39553.10.3.8.136
    ex2HumitureTemperatureSensorMinimumValue OBJECT-TYPE
    SYNTAX INTEGER (-4000..10000)
    MAX-ACCESS read-write
    STATUS current
    DESCRIPTION 
        "The lower limit for the EX2-Humiture Temperature sensor sample range.
        The actual value = The set or receive data / 100."
    ::= { dcParameter 136 }
  -- 1.3.6.1.4.1.39553.10.3.8.137
    ex2HumitureTemperatureSensorMaximumValue OBJECT-TYPE
    SYNTAX INTEGER (-4000..10000)
    MAX-ACCESS read-write
    STATUS current
    DESCRIPTION 
        "The upper limit for the EX2-Humiture Temperature sensor sample range.
        The actual value = The set or receive data / 100."
    ::= { dcParameter 137 }
  -- 1.3.6.1.4.1.39553.10.3.8.138
    ex3HumitureTemperatureSensorMinimumValue OBJECT-TYPE
    SYNTAX INTEGER (-4000..10000)
    MAX-ACCESS read-write
    STATUS current
    DESCRIPTION 
        "The lower limit for the EX3-Humiture Temperature sensor sample range.
        The actual value = The set or receive data / 100."
    ::= { dcParameter 138 }
  -- 1.3.6.1.4.1.39553.10.3.8.139
    ex3HumitureTemperatureSensorMaximumValue OBJECT-TYPE
    SYNTAX INTEGER (-4000..10000)
    MAX-ACCESS read-write
    STATUS current
    DESCRIPTION 
        "The upper limit for the EX3-Humiture Temperature sensor sample range.
        The actual value = The set or receive data / 100."
    ::= { dcParameter 139 }
  -- 1.3.6.1.4.1.39553.10.3.8.140
    ex4HumitureTemperatureSensorMinimumValue OBJECT-TYPE
    SYNTAX INTEGER (-4000..10000)
    MAX-ACCESS read-write
    STATUS current
    DESCRIPTION 
        "The lower limit for the EX4-Humiture Temperature sensor sample range.
        The actual value = The set or receive data / 100."
    ::= { dcParameter 140 }
  -- 1.3.6.1.4.1.39553.10.3.8.141
    ex4HumitureTemperatureSensorMaximumValue OBJECT-TYPE
    SYNTAX INTEGER (-4000..10000)
    MAX-ACCESS read-write
    STATUS current
    DESCRIPTION 
        "The upper limit for the EX4-Humiture Temperature sensor sample range.
        The actual value = The set or receive data / 100."
    ::= { dcParameter 141 }
  -- 1.3.6.1.4.1.39553.10.3.8.142
    ex5HumitureTemperatureSensorMinimumValue OBJECT-TYPE
    SYNTAX INTEGER (-4000..10000)
    MAX-ACCESS read-write
    STATUS current
    DESCRIPTION 
        "The lower limit for the EX5-Humiture Temperature sensor sample range.
        The actual value = The set or receive data / 100."
    ::= { dcParameter 142 }
  -- 1.3.6.1.4.1.39553.10.3.8.143
    ex5HumitureTemperatureSensorMaximumValue OBJECT-TYPE
    SYNTAX INTEGER (-4000..10000)
    MAX-ACCESS read-write
    STATUS current
    DESCRIPTION 
        "The upper limit for the EX5-Humiture Temperature sensor sample range.
        The actual value = The set or receive data / 100."
    ::= { dcParameter 143 }
    
-----------------------------------------------------------------------
--  DC Distribution Componen Parameter { dpcDistributedPower 9 }
------------------------------------------------------------------------
-- 1.3.6.1.4.1.39553.10.3.9
    componenParameter OBJECT IDENTIFIER ::= { dcDistribution 9 }
    
  -- 1.3.6.1.4.1.39553.10.3.9.4
    sc501BATT1SHVoltage OBJECT-TYPE
    SYNTAX INTEGER(25..50)
    UNITS   "mV; i.e. 25 = 25mV"
    MAX-ACCESS read-write
    STATUS current
    DESCRIPTION
    "SC501 BATT1 shunt rated voltage
    UNITS mV; i.e. 25 = 25mV
    "
    ::= { componenParameter 4 }
  -- 1.3.6.1.4.1.39553.10.3.9.5
    sc501BATT1SHCurrent OBJECT-TYPE
    SYNTAX INTEGER(25..3000)
    UNITS   "Ampere; i.e. 3000 = 3000Ampere"
    MAX-ACCESS read-write
    STATUS current
    DESCRIPTION
    "SC501 BATT1 shunt rated current
    UNITS Ampere; i.e. 3000 = 3000Ampere
    "
    ::= { componenParameter 5 }
    -- 1.3.6.1.4.1.39553.10.3.9.6
    sc501BATT2SHVoltage OBJECT-TYPE
    SYNTAX INTEGER(25..50)
    UNITS   "mV; i.e. 25 = 25mV"
    MAX-ACCESS read-write
    STATUS current
    DESCRIPTION
    "SC501 BATT2 shunt rated voltage
    UNITS mV; i.e. 25 = 25mV
    "
    ::= { componenParameter 6 }
    -- 1.3.6.1.4.1.39553.10.3.9.7
    
    sc501BATT2SHCurrent OBJECT-TYPE
    SYNTAX INTEGER(25..3000)
    UNITS   "Ampere; i.e. 3000 = 3000Ampere"
    MAX-ACCESS read-write
    STATUS current
    DESCRIPTION
    "SC501 BATT2 shunt rated current
    UNITS Ampere; i.e. 3000 = 3000Ampere
    "
    ::= { componenParameter 7 }
  -- 1.3.6.1.4.1.39553.10.3.9.8
    sc501LOADShuntVoltage OBJECT-TYPE
    SYNTAX INTEGER(25..50)
    UNITS   "mV; i.e. 25 = 25mV"
    MAX-ACCESS read-write
    STATUS current
    DESCRIPTION
    "SC501 load current shunt rated voltage
    UNITS mV; i.e. 25 = 25mV
    "
    ::= { componenParameter 8 }
  -- 1.3.6.1.4.1.39553.10.3.9.9
    sc501LOADShuntCurrent OBJECT-TYPE
    SYNTAX INTEGER(25..3000)
    UNITS   "Ampere; i.e. 3000 = 3000Ampere"
    MAX-ACCESS read-write
    STATUS current
    DESCRIPTION
    "SC501 load current shunt rated current
    UNITS Ampere; i.e. 3000 = 3000Ampere
    "
    ::= { componenParameter 9 }
    -- 1.3.6.1.4.1.39553.10.3.9.10
    spdAlarmState OBJECT-TYPE
    SYNTAX INTEGER {
    nc(0),
    no(1)
    }
    MAX-ACCESS read-write
    STATUS current
    DESCRIPTION
    "DI state when SPD alarm
    0:NC;
    1:NO;
    "
    ::= { componenParameter 10 }
    -- 1.3.6.1.4.1.39553.10.3.9.101
    sc210_1I_BAT1ShuntCurrent OBJECT-TYPE
    SYNTAX INTEGER(25..3000)
    UNITS   "Ampere; i.e. 3000 = 3000Ampere"
    MAX-ACCESS read-write
    STATUS current
    DESCRIPTION
    "SC210-1 battery current 1 shunt rated current
    UNITS Ampere; i.e. 3000 = 3000Ampere
    "
    ::= { componenParameter 101 }
    -- 1.3.6.1.4.1.39553.10.3.9.102
    sc210_1I_BAT2ShuntCurrent OBJECT-TYPE
    SYNTAX INTEGER(25..3000)
    UNITS   "Ampere; i.e. 3000 = 3000Ampere"
    MAX-ACCESS read-write
    STATUS current
    DESCRIPTION
    "SC210-1 battery current 2 shunt rated current
    UNITS Ampere; i.e. 3000 = 3000Ampere
    "
    ::= { componenParameter 102 }
    -- 1.3.6.1.4.1.39553.10.3.9.103
    sc210_1I_BAT3ShuntCurrent OBJECT-TYPE
    SYNTAX INTEGER(25..3000)
    UNITS   "Ampere; i.e. 3000 = 3000Ampere"
    MAX-ACCESS read-write
    STATUS current
    DESCRIPTION
    "SC210-1 battery current 3 shunt rated current
    UNITS Ampere; i.e. 3000 = 3000Ampere
    "
    ::= { componenParameter 103 }
    -- 1.3.6.1.4.1.39553.10.3.9.104
    sc210_1I_BAT1ShuntVoltage OBJECT-TYPE
    SYNTAX INTEGER(25..50)
    UNITS   "mV; i.e. 25 = 25mV"
    MAX-ACCESS read-write
    STATUS current
    DESCRIPTION
    "SC210-1 battery current 1 shunt rated voltage
    UNITS mV; i.e. 25 = 25mV
    "
    ::= { componenParameter 104 }
    -- 1.3.6.1.4.1.39553.10.3.9.105
    sc210_1I_BAT2ShuntVoltage OBJECT-TYPE
    SYNTAX INTEGER(25..50)
    UNITS   "mV; i.e. 25 = 25mV"
    MAX-ACCESS read-write
    STATUS current
    DESCRIPTION
    "SC210-1 battery current 2 shunt rated voltage
    UNITS mV; i.e. 25 = 25mV
    "
    ::= { componenParameter 105 }
    -- 1.3.6.1.4.1.39553.10.3.9.106
    sc210_1I_BAT3ShuntVoltage OBJECT-TYPE
    SYNTAX INTEGER(25..50)
    UNITS   "mV; i.e. 25 = 25mV"
    MAX-ACCESS read-write
    STATUS current
    DESCRIPTION
    "SC210-1 battery current 3 shunt rated voltage
    UNITS mV; i.e. 25 = 25mV
    "
    ::= { componenParameter 106 }
    -- 1.3.6.1.4.1.39553.10.3.9.107
    sc210_1I_LOAD1ShuntCurrent OBJECT-TYPE
    SYNTAX INTEGER(25..3000)
    UNITS   "Ampere; i.e. 3000 = 3000Ampere"
    MAX-ACCESS read-write
    STATUS current
    DESCRIPTION
    "SC210-1 load current 1 shunt rated current
    UNITS Ampere; i.e. 3000 = 3000Ampere
    "
    ::= { componenParameter 107 }
    -- 1.3.6.1.4.1.39553.10.3.9.108
    sc210_1I_LOAD2ShuntCurrent OBJECT-TYPE
    SYNTAX INTEGER(25..3000)
    UNITS   "Ampere; i.e. 3000 = 3000Ampere"
    MAX-ACCESS read-write
    STATUS current
    DESCRIPTION
    "SC210-1 load current 2 shunt rated current
    UNITS Ampere; i.e. 3000 = 3000Ampere
    "
    ::= { componenParameter 108 }
    -- 1.3.6.1.4.1.39553.10.3.9.109
    sc210_1I_LOAD3ShuntCurrent OBJECT-TYPE
    SYNTAX INTEGER(25..3000)
    UNITS   "Ampere; i.e. 3000 = 3000Ampere"
    MAX-ACCESS read-write
    STATUS current
    DESCRIPTION
    "SC210-1 load current 3 shunt rated current
    UNITS Ampere; i.e. 3000 = 3000Ampere
    "
    ::= { componenParameter 109 }
    -- 1.3.6.1.4.1.39553.10.3.9.110
    sc210_1I_LOAD1ShuntVoltage OBJECT-TYPE
    SYNTAX INTEGER(25..50)
    UNITS   "mV; i.e. 25 = 25mV"
    MAX-ACCESS read-write
    STATUS current
    DESCRIPTION
    "SC210-1 load current 1 shunt rated voltage
    UNITS mV; i.e. 25 = 25mV
    "
    ::= { componenParameter 110 }
    -- 1.3.6.1.4.1.39553.10.3.9.111
    sc210_1I_LOAD2ShuntVoltage OBJECT-TYPE
    SYNTAX INTEGER(25..50)
    UNITS   "mV; i.e. 25 = 25mV"
    MAX-ACCESS read-write
    STATUS current
    DESCRIPTION
    "SC210-1 load current 2 shunt rated voltage
    UNITS mV; i.e. 25 = 25mV
    "
    ::= { componenParameter 111 }
    -- 1.3.6.1.4.1.39553.10.3.9.112
    sc210_1I_LOAD3ShuntVoltage OBJECT-TYPE
    SYNTAX INTEGER(25..50)
    UNITS   "mV; i.e. 25 = 25mV"
    MAX-ACCESS read-write
    STATUS current
    DESCRIPTION
    "SC210-1 load current 3 shunt rated voltage
    UNITS mV; i.e. 25 = 25mV
    "
    ::= { componenParameter 112 }
    -- 1.3.6.1.4.1.39553.10.3.9.113
    sc210_1I_LOAD4ShuntCurrent OBJECT-TYPE
    SYNTAX INTEGER(25..3000)
    UNITS   "Ampere; i.e. 3000 = 3000Ampere"
    MAX-ACCESS read-write
    STATUS current
    DESCRIPTION
    "SC210-1 load current 4 shunt rated current
    UNITS Ampere; i.e. 3000 = 3000Ampere
    "
    ::= { componenParameter 113 }
    -- 1.3.6.1.4.1.39553.10.3.9.114
    sc210_1I_LOAD4ShuntVoltage OBJECT-TYPE
    SYNTAX INTEGER(25..50)
    UNITS   "mV; i.e. 25 = 25mV"
    MAX-ACCESS read-write
    STATUS current
    DESCRIPTION
    "SC210-1 load current 4 shunt rated voltage
    UNITS mV; i.e. 25 = 25mV
    "
    ::= { componenParameter 114 }
  -- 1.3.6.1.4.1.39553.10.3.9.115
    sc210_1IHallCurrent OBJECT-TYPE
    SYNTAX INTEGER(0..2000)
    UNITS   "Ampere; i.e. 2000 = 2000Ampere"
    MAX-ACCESS read-write
    STATUS current
    DESCRIPTION
    "SC210-1  hall current rated current
    UNITS Ampere; i.e. 2000 = 2000Ampere
    "
    ::= { componenParameter 115 }
  -- 1.3.6.1.4.1.39553.10.3.9.116
    sc210_1IHallVoltH OBJECT-TYPE
    SYNTAX INTEGER(0..500)
    UNITS   "V; i.e. 500 = 5V"
    MAX-ACCESS read-write
    STATUS current
    DESCRIPTION
    "SC210-1 hall current voltage upper limit,
    The actual value =The set or receive data / 100.
    UNITS V; i.e. 500 = 5V
    "
    ::= { componenParameter 116 }
  -- 1.3.6.1.4.1.39553.10.3.9.117
    sc210_1IHallVoltL OBJECT-TYPE
    SYNTAX INTEGER(0..500)
    UNITS   "V; i.e. 500 = 5V"
    MAX-ACCESS read-write
    STATUS current
    DESCRIPTION
    "SC210-1 hall current voltage lower limit,
    The actual value =The set or receive data / 100.
    UNITS V; i.e. 500 = 5V
    "
    ::= { componenParameter 117 }
    -- 1.3.6.1.4.1.39553.10.3.9.118
    sc210_1LoadBranNumber OBJECT-TYPE
    SYNTAX INTEGER(0..4)
    MAX-ACCESS read-write
    STATUS current
    DESCRIPTION
    "SC210-1 load branch number,
    "
    ::= { componenParameter 118 }
    -- 1.3.6.1.4.1.39553.10.3.9.201
    sc210_2I_BAT1ShuntCurrent OBJECT-TYPE
    SYNTAX INTEGER(25..3000)
    UNITS   "Ampere; i.e. 3000 = 3000Ampere"
    MAX-ACCESS read-write
    STATUS current
    DESCRIPTION
    "SC210-2 battery current 1 shunt rated current
    UNITS Ampere; i.e. 3000 = 3000Ampere
    "
    ::= { componenParameter 201 }
    -- 1.3.6.1.4.1.39553.10.3.9.202
    sc210_2I_BAT2ShuntCurrent OBJECT-TYPE
    SYNTAX INTEGER(25..3000)
    UNITS   "Ampere; i.e. 3000 = 3000Ampere"
    MAX-ACCESS read-write
    STATUS current
    DESCRIPTION
    "SC210-2 battery current 2 shunt rated current
    UNITS Ampere; i.e. 3000 = 3000Ampere
    "
    ::= { componenParameter 202 }
    -- 1.3.6.1.4.1.39553.10.3.9.203
    sc210_2I_BAT3ShuntCurrent OBJECT-TYPE
    SYNTAX INTEGER(25..3000)
    UNITS   "Ampere; i.e. 3000 = 3000Ampere"
    MAX-ACCESS read-write
    STATUS current
    DESCRIPTION
    "SC210-2 battery current 3 shunt rated current
    UNITS Ampere; i.e. 3000 = 3000Ampere
    "
    ::= { componenParameter 203 }
    -- 1.3.6.1.4.1.39553.10.3.9.204
    sc210_2I_BAT1ShuntVoltage OBJECT-TYPE
    SYNTAX INTEGER(25..50)
    UNITS   "mV; i.e. 25 = 25mV"
    MAX-ACCESS read-write
    STATUS current
    DESCRIPTION
    "SC210-2 battery current 1 shunt rated voltage
    UNITS mV; i.e. 25 = 25mV
    "
    ::= { componenParameter 204 }
    -- 1.3.6.1.4.1.39553.10.3.9.205
    sc210_2I_BAT2ShuntVoltage OBJECT-TYPE
    SYNTAX INTEGER(25..50)
    UNITS   "mV; i.e. 25 = 25mV"
    MAX-ACCESS read-write
    STATUS current
    DESCRIPTION
    "SC210-2 battery current 2 shunt rated voltage
    UNITS mV; i.e. 25 = 25mV
    "
    ::= { componenParameter 205 }
    -- 1.3.6.1.4.1.39553.10.3.9.206
    sc210_2I_BAT3ShuntVoltage OBJECT-TYPE
    SYNTAX INTEGER(25..50)
    UNITS   "mV; i.e. 25 = 25mV"
    MAX-ACCESS read-write
    STATUS current
    DESCRIPTION
    "SC210-2 battery current 3 shunt rated voltage
    UNITS mV; i.e. 25 = 25mV
    "
    ::= { componenParameter 206 }
    -- 1.3.6.1.4.1.39553.10.3.9.207
    sc210_2I_LOAD1ShuntCurrent OBJECT-TYPE
    SYNTAX INTEGER(25..3000)
    UNITS   "Ampere; i.e. 3000 = 3000Ampere"
    MAX-ACCESS read-write
    STATUS current
    DESCRIPTION
    "SC210-2 load current 1 shunt rated current
    UNITS Ampere; i.e. 3000 = 3000Ampere
    "
    ::= { componenParameter 207 }
    -- 1.3.6.1.4.1.39553.10.3.9.208
    sc210_2I_LOAD2ShuntCurrent OBJECT-TYPE
    SYNTAX INTEGER(25..3000)
    UNITS   "Ampere; i.e. 3000 = 3000Ampere"
    MAX-ACCESS read-write
    STATUS current
    DESCRIPTION
    "SC210-2 load current 2 shunt rated current
    UNITS Ampere; i.e. 3000 = 3000Ampere
    "
    ::= { componenParameter 208 }
    -- 1.3.6.1.4.1.39553.10.3.9.209
    sc210_2I_LOAD3ShuntCurrent OBJECT-TYPE
    SYNTAX INTEGER(25..3000)
    UNITS   "Ampere; i.e. 3000 = 3000Ampere"
    MAX-ACCESS read-write
    STATUS current
    DESCRIPTION
    "SC210-2 load current 3 shunt rated current
    UNITS Ampere; i.e. 3000 = 3000Ampere
    "
    ::= { componenParameter 209 }
    -- 1.3.6.1.4.1.39553.10.3.9.210
    sc210_2I_LOAD1ShuntVoltage OBJECT-TYPE
    SYNTAX INTEGER(25..50)
    UNITS   "mV; i.e. 25 = 25mV"
    MAX-ACCESS read-write
    STATUS current
    DESCRIPTION
    "SC210-2 load current 1 shunt rated voltage
    UNITS mV; i.e. 25 = 25mV
    "
    ::= { componenParameter 210 }
    -- 1.3.6.1.4.1.39553.10.3.9.211
    sc210_2I_LOAD2ShuntVoltage OBJECT-TYPE
    SYNTAX INTEGER(25..50)
    UNITS   "mV; i.e. 25 = 25mV"
    MAX-ACCESS read-write
    STATUS current
    DESCRIPTION
    "SC210-2 load current 2 shunt rated voltage
    UNITS mV; i.e. 25 = 25mV
    "
    ::= { componenParameter 211 }
    -- 1.3.6.1.4.1.39553.10.3.9.212
    sc210_2I_LOAD3ShuntVoltage OBJECT-TYPE
    SYNTAX INTEGER(25..50)
    UNITS   "mV; i.e. 25 = 25mV"
    MAX-ACCESS read-write
    STATUS current
    DESCRIPTION
    "SC210-2 load current 3 shunt rated voltage
    UNITS mV; i.e. 25 = 25mV
    "
    ::= { componenParameter 212 }
    -- 1.3.6.1.4.1.39553.10.3.9.213
    sc210_2I_LOAD4ShuntCurrent OBJECT-TYPE
    SYNTAX INTEGER(25..3000)
    UNITS   "Ampere; i.e. 3000 = 3000Ampere"
    MAX-ACCESS read-write
    STATUS current
    DESCRIPTION
    "SC210-2 load current 4 shunt rated current
    UNITS Ampere; i.e. 3000 = 3000Ampere
    "
    ::= { componenParameter 213 }
    -- 1.3.6.1.4.1.39553.10.3.9.214
    sc210_2I_LOAD4ShuntVoltage OBJECT-TYPE
    SYNTAX INTEGER(25..50)
    UNITS   "mV; i.e. 25 = 25mV"
    MAX-ACCESS read-write
    STATUS current
    DESCRIPTION
    "SC210-2 load current 4 shunt rated voltage
    UNITS mV; i.e. 25 = 25mV
    "
    ::= { componenParameter 214 }
  -- 1.3.6.1.4.1.39553.10.3.9.215
    sc210_2IHallCurrent OBJECT-TYPE
    SYNTAX INTEGER(0..2000)
    UNITS   "Ampere; i.e. 2000 = 2000Ampere"
    MAX-ACCESS read-write
    STATUS current
    DESCRIPTION
    "SC210-2  hall current rated current
    UNITS Ampere; i.e. 2000 = 2000Ampere
    "
    ::= { componenParameter 215 }
  -- 1.3.6.1.4.1.39553.10.3.9.216
    sc210_2IHallVoltH OBJECT-TYPE
    SYNTAX INTEGER(0..500)
    UNITS   "V; i.e. 500 = 5V"
    MAX-ACCESS read-write
    STATUS current
    DESCRIPTION
    "SC210-2 hall current voltage upper limit,
    The actual value =The set or receive data / 100.
    UNITS V; i.e. 500 = 5V
    "
    ::= { componenParameter 216 }
  -- 1.3.6.1.4.1.39553.10.3.9.217
    sc210_2IHallVoltL OBJECT-TYPE
    SYNTAX INTEGER(0..500)
    UNITS   "V; i.e. 500 = 5V"
    MAX-ACCESS read-write
    STATUS current
    DESCRIPTION
    "SC210-2 hall current voltage lower limit,
    The actual value =The set or receive data / 100.
    UNITS V; i.e. 500 = 5V
    "
    ::= { componenParameter 217 }
    -- 1.3.6.1.4.1.39553.10.3.9.218
    sc210_2LoadBranNumber OBJECT-TYPE
    SYNTAX INTEGER(0..4)
    MAX-ACCESS read-write
    STATUS current
    DESCRIPTION
    "SC210-2 load branch number,
    "
    ::= { componenParameter 218 }
  -- 1.3.6.1.4.1.39553.10.3.9.401
    sc320_1DONumber OBJECT-TYPE
    SYNTAX INTEGER{
        zero(0),
        eight(8),
        sixteen(16)
    }
    MAX-ACCESS read-write
    STATUS current
    DESCRIPTION
    "SC320-1 DO number
    "
    ::= { componenParameter 401 }
  -- 1.3.6.1.4.1.39553.10.3.9.402
    sc320_2DONumber OBJECT-TYPE
    SYNTAX INTEGER{
        zero(0),
        eight(8),
        sixteen(16)
    }
    MAX-ACCESS read-write
    STATUS current
    DESCRIPTION
    "SC320-2 DO number
    "
    ::= { componenParameter 402 }
  -- 1.3.6.1.4.1.39553.10.3.9.403
    sc320_3DONumber OBJECT-TYPE
    SYNTAX INTEGER{
        zero(0),
        eight(8),
        sixteen(16)
    }
    MAX-ACCESS read-write
    STATUS current
    DESCRIPTION
    "SC320-3 DO number
    "
    ::= { componenParameter 403 }
  -- 1.3.6.1.4.1.39553.10.3.9.404
    sc320_4DONumber OBJECT-TYPE
    SYNTAX INTEGER{
        zero(0),
        eight(8),
        sixteen(16)
    }
    MAX-ACCESS read-write
    STATUS current
    DESCRIPTION
    "SC320-4 DO number
    "
    ::= { componenParameter 404 }
  -- 1.3.6.1.4.1.39553.10.3.9.405
    sc320_5DONumber OBJECT-TYPE
    SYNTAX INTEGER{
        zero(0),
        eight(8),
        sixteen(16)
    }
    MAX-ACCESS read-write
    STATUS current
    DESCRIPTION
    "SC320-5 DO number
    "
    ::= { componenParameter 405 }
        
            -- 1.3.6.1.4.1.39553.10.3.10
        digitalInputAndOutputParameter OBJECT IDENTIFIER ::= { dcDistribution 10 }  
        
  -- 1.3.6.1.4.1.39553.10.3.10.1
    do1AlarmState OBJECT-TYPE
    SYNTAX INTEGER {
    no(0),
    nc(1)
    }
    MAX-ACCESS read-write
    STATUS current
    DESCRIPTION
    "DO1 output state when alarm happen
    0:NO;
    1:NC
    "
    ::= { digitalInputAndOutputParameter 1 }
    -- 1.3.6.1.4.1.39553.10.3.10.2
    do2AlarmState OBJECT-TYPE
    SYNTAX INTEGER {
    no(0),
    nc(1)
    }
    MAX-ACCESS read-write
    STATUS current
    DESCRIPTION
    "DO2 output state when alarm happen
    0:NO;
    1:NC
    "
    ::= { digitalInputAndOutputParameter 2 }
    -- 1.3.6.1.4.1.39553.10.3.10.3
    do3AlarmState OBJECT-TYPE
    SYNTAX INTEGER {
    no(0),
    nc(1)
    }
    MAX-ACCESS read-write
    STATUS current
    DESCRIPTION
    "DO3 output state when alarm happen
    0:NO;
    1:NC
    "
    ::= { digitalInputAndOutputParameter 3 }
    -- 1.3.6.1.4.1.39553.10.3.10.4
    do4AlarmState OBJECT-TYPE
    SYNTAX INTEGER {
    no(0),
    nc(1)
    }
    MAX-ACCESS read-write
    STATUS current
    DESCRIPTION
    "DO4 output state when alarm happen
    0:NO;
    1:NC
    "
    ::= { digitalInputAndOutputParameter 4 }
    -- 1.3.6.1.4.1.39553.10.3.10.5
    do5AlarmState OBJECT-TYPE
    SYNTAX INTEGER {
    no(0),
    nc(1)
    }
    MAX-ACCESS read-write
    STATUS current
    DESCRIPTION
    "DO5 output state when alarm happen
    0:NO;
    1:NC
    "
    ::= { digitalInputAndOutputParameter 5 }
    -- 1.3.6.1.4.1.39553.10.3.10.6
    do6AlarmState OBJECT-TYPE
    SYNTAX INTEGER {
    no(0),
    nc(1)
    }
    MAX-ACCESS read-write
    STATUS current
    DESCRIPTION
    "DO6 output state when alarm happen
    0:NO;
    1:NC
    "
    ::= { digitalInputAndOutputParameter 6 }
    -- 1.3.6.1.4.1.39553.10.3.10.7
    ex1DO1AlarmState OBJECT-TYPE
    SYNTAX INTEGER {
    no(0),
    nc(1)
    }
    MAX-ACCESS read-write
    STATUS current
    DESCRIPTION
    "EX1-DO1 output state when alarm happen
    0:NO;
    1:NC
    "
    ::= { digitalInputAndOutputParameter 7 }
    -- 1.3.6.1.4.1.39553.10.3.10.8
    ex1DO2AlarmState OBJECT-TYPE
    SYNTAX INTEGER {
    no(0),
    nc(1)
    }
    MAX-ACCESS read-write
    STATUS current
    DESCRIPTION
    "EX1-DO2 output state when alarm happen
    0:NO;
    1:NC
    "
    ::= { digitalInputAndOutputParameter 8 }
    -- 1.3.6.1.4.1.39553.10.3.10.9
    ex1DO3AlarmState OBJECT-TYPE
    SYNTAX INTEGER {
    no(0),
    nc(1)
    }
    MAX-ACCESS read-write
    STATUS current
    DESCRIPTION
    "EX1-DO3 output state when alarm happen
    0:NO;
    1:NC
    "
    ::= { digitalInputAndOutputParameter 9 }
    -- 1.3.6.1.4.1.39553.10.3.10.10
    ex1DO4AlarmState OBJECT-TYPE
    SYNTAX INTEGER {
    no(0),
    nc(1)
    }
    MAX-ACCESS read-write
    STATUS current
    DESCRIPTION
    "EX1-DO4 output state when alarm happen
    0:NO;
    1:NC
    "
    ::= { digitalInputAndOutputParameter 10 }
    -- 1.3.6.1.4.1.39553.10.3.10.11
    ex1DO5AlarmState OBJECT-TYPE
    SYNTAX INTEGER {
    no(0),
    nc(1)
    }
    MAX-ACCESS read-write
    STATUS current
    DESCRIPTION
    "EX1-DO5 output state when alarm happen
    0:NO;
    1:NC
    "
    ::= { digitalInputAndOutputParameter 11 }
    -- 1.3.6.1.4.1.39553.10.3.10.12
    ex1DO6AlarmState OBJECT-TYPE
    SYNTAX INTEGER {
    no(0),
    nc(1)
    }
    MAX-ACCESS read-write
    STATUS current
    DESCRIPTION
    "EX1-DO6 output state when alarm happen
    0:NO;
    1:NC
    "
    ::= { digitalInputAndOutputParameter 12 }
    -- 1.3.6.1.4.1.39553.10.3.10.13
    ex1DO7AlarmState OBJECT-TYPE
    SYNTAX INTEGER {
    no(0),
    nc(1)
    }
    MAX-ACCESS read-write
    STATUS current
    DESCRIPTION
    "EX1-DO7 output state when alarm happen
    0:NO;
    1:NC
    "
    ::= { digitalInputAndOutputParameter 13 }
    -- 1.3.6.1.4.1.39553.10.3.10.14
    ex1DO8AlarmState OBJECT-TYPE
    SYNTAX INTEGER {
    no(0),
    nc(1)
    }
    MAX-ACCESS read-write
    STATUS current
    DESCRIPTION
    "EX1-DO8 output state when alarm happen
    0:NO;
    1:NC
    "
    ::= { digitalInputAndOutputParameter 14 }
    -- 1.3.6.1.4.1.39553.10.3.10.15
    ex1DO9AlarmState OBJECT-TYPE
    SYNTAX INTEGER {
    no(0),
    nc(1)
    }
    MAX-ACCESS read-write
    STATUS current
    DESCRIPTION
    "EX1-DO9 output state when alarm happen
    0:NO;
    1:NC
    "
    ::= { digitalInputAndOutputParameter 15 }
    -- 1.3.6.1.4.1.39553.10.3.10.16
    ex1DO10AlarmState OBJECT-TYPE
    SYNTAX INTEGER {
    no(0),
    nc(1)
    }
    MAX-ACCESS read-write
    STATUS current
    DESCRIPTION
    "EX1-DO10 output state when alarm happen
    0:NO;
    1:NC
    "
    ::= { digitalInputAndOutputParameter 16 }
    -- 1.3.6.1.4.1.39553.10.3.10.17
    ex1DO11AlarmState OBJECT-TYPE
    SYNTAX INTEGER {
    no(0),
    nc(1)
    }
    MAX-ACCESS read-write
    STATUS current
    DESCRIPTION
    "EX1-DO11 output state when alarm happen
    0:NO;
    1:NC
    "
    ::= { digitalInputAndOutputParameter 17 }
    -- 1.3.6.1.4.1.39553.10.3.10.18
    ex1DO12AlarmState OBJECT-TYPE
    SYNTAX INTEGER {
    no(0),
    nc(1)
    }
    MAX-ACCESS read-write
    STATUS current
    DESCRIPTION
    "EX1-DO12 output state when alarm happen
    0:NO;
    1:NC
    "
    ::= { digitalInputAndOutputParameter 18 }
    -- 1.3.6.1.4.1.39553.10.3.10.19
    ex1DO13AlarmState OBJECT-TYPE
    SYNTAX INTEGER {
    no(0),
    nc(1)
    }
    MAX-ACCESS read-write
    STATUS current
    DESCRIPTION
    "EX1-DO13 output state when alarm happen
    0:NO;
    1:NC
    "
    ::= { digitalInputAndOutputParameter 19 }
    -- 1.3.6.1.4.1.39553.10.3.10.20
    ex1DO14AlarmState OBJECT-TYPE
    SYNTAX INTEGER {
    no(0),
    nc(1)
    }
    MAX-ACCESS read-write
    STATUS current
    DESCRIPTION
    "EX1-DO14 output state when alarm happen
    0:NO;
    1:NC
    "
    ::= { digitalInputAndOutputParameter 20 }
    -- 1.3.6.1.4.1.39553.10.3.10.21
    ex1DO15AlarmState OBJECT-TYPE
    SYNTAX INTEGER {
    no(0),
    nc(1)
    }
    MAX-ACCESS read-write
    STATUS current
    DESCRIPTION
    "EX1-DO15 output state when alarm happen
    0:NO;
    1:NC
    "
    ::= { digitalInputAndOutputParameter 21 }
    -- 1.3.6.1.4.1.39553.10.3.10.22
    ex1DO16AlarmState OBJECT-TYPE
    SYNTAX INTEGER {
    no(0),
    nc(1)
    }
    MAX-ACCESS read-write
    STATUS current
    DESCRIPTION
    "EX1-DO16 output state when alarm happen
    0:NO;
    1:NC
    "
    ::= { digitalInputAndOutputParameter 22 }
    -- 1.3.6.1.4.1.39553.10.3.10.23
    ex2DO1AlarmState OBJECT-TYPE
    SYNTAX INTEGER {
    no(0),
    nc(1)
    }
    MAX-ACCESS read-write
    STATUS current
    DESCRIPTION
    "EX2-DO1 output state when alarm happen
    0:NO;
    1:NC
    "
    ::= { digitalInputAndOutputParameter 23 }
    -- 1.3.6.1.4.1.39553.10.3.10.24
    ex2DO2AlarmState OBJECT-TYPE
    SYNTAX INTEGER {
    no(0),
    nc(1)
    }
    MAX-ACCESS read-write
    STATUS current
    DESCRIPTION
    "EX2-DO2 output state when alarm happen
    0:NO;
    1:NC
    "
    ::= { digitalInputAndOutputParameter 24 }
    -- 1.3.6.1.4.1.39553.10.3.10.25
    ex2DO3AlarmState OBJECT-TYPE
    SYNTAX INTEGER {
    no(0),
    nc(1)
    }
    MAX-ACCESS read-write
    STATUS current
    DESCRIPTION
    "EX2-DO3 output state when alarm happen
    0:NO;
    1:NC
    "
    ::= { digitalInputAndOutputParameter 25 }
    -- 1.3.6.1.4.1.39553.10.3.10.26
    ex2DO4AlarmState OBJECT-TYPE
    SYNTAX INTEGER {
    no(0),
    nc(1)
    }
    MAX-ACCESS read-write
    STATUS current
    DESCRIPTION
    "EX2-DO4 output state when alarm happen
    0:NO;
    1:NC
    "
    ::= { digitalInputAndOutputParameter 26 }
    -- 1.3.6.1.4.1.39553.10.3.10.27
    ex2DO5AlarmState OBJECT-TYPE
    SYNTAX INTEGER {
    no(0),
    nc(1)
    }
    MAX-ACCESS read-write
    STATUS current
    DESCRIPTION
    "EX2-DO5 output state when alarm happen
    0:NO;
    1:NC
    "
    ::= { digitalInputAndOutputParameter 27 }
    -- 1.3.6.1.4.1.39553.10.3.10.28
    ex2DO6AlarmState OBJECT-TYPE
    SYNTAX INTEGER {
    no(0),
    nc(1)
    }
    MAX-ACCESS read-write
    STATUS current
    DESCRIPTION
    "EX2-DO6 output state when alarm happen
    0:NO;
    1:NC
    "
    ::= { digitalInputAndOutputParameter 28 }
    -- 1.3.6.1.4.1.39553.10.3.10.29
    ex2DO7AlarmState OBJECT-TYPE
    SYNTAX INTEGER {
    no(0),
    nc(1)
    }
    MAX-ACCESS read-write
    STATUS current
    DESCRIPTION
    "EX2-DO7 output state when alarm happen
    0:NO;
    1:NC
    "
    ::= { digitalInputAndOutputParameter 29 }
    -- 1.3.6.1.4.1.39553.10.3.10.30
    ex2DO8AlarmState OBJECT-TYPE
    SYNTAX INTEGER {
    no(0),
    nc(1)
    }
    MAX-ACCESS read-write
    STATUS current
    DESCRIPTION
    "EX2-DO8 output state when alarm happen
    0:NO;
    1:NC
    "
    ::= { digitalInputAndOutputParameter 30 }
    -- 1.3.6.1.4.1.39553.10.3.10.31
    ex2DO9AlarmState OBJECT-TYPE
    SYNTAX INTEGER {
    no(0),
    nc(1)
    }
    MAX-ACCESS read-write
    STATUS current
    DESCRIPTION
    "EX2-DO9 output state when alarm happen
    0:NO;
    1:NC
    "
    ::= { digitalInputAndOutputParameter 31 }
    -- 1.3.6.1.4.1.39553.10.3.10.32
    ex2DO10AlarmState OBJECT-TYPE
    SYNTAX INTEGER {
    no(0),
    nc(1)
    }
    MAX-ACCESS read-write
    STATUS current
    DESCRIPTION
    "EX2-DO10 output state when alarm happen
    0:NO;
    1:NC
    "
    ::= { digitalInputAndOutputParameter 32 }
    -- 1.3.6.1.4.1.39553.10.3.10.33
    ex2DO11AlarmState OBJECT-TYPE
    SYNTAX INTEGER {
    no(0),
    nc(1)
    }
    MAX-ACCESS read-write
    STATUS current
    DESCRIPTION
    "EX2-DO11 output state when alarm happen
    0:NO;
    1:NC
    "
    ::= { digitalInputAndOutputParameter 33 }
    -- 1.3.6.1.4.1.39553.10.3.10.34
    ex2DO12AlarmState OBJECT-TYPE
    SYNTAX INTEGER {
    no(0),
    nc(1)
    }
    MAX-ACCESS read-write
    STATUS current
    DESCRIPTION
    "EX2-DO12 output state when alarm happen
    0:NO;
    1:NC
    "
    ::= { digitalInputAndOutputParameter 34 }
    -- 1.3.6.1.4.1.39553.10.3.10.35
    ex2DO13AlarmState OBJECT-TYPE
    SYNTAX INTEGER {
    no(0),
    nc(1)
    }
    MAX-ACCESS read-write
    STATUS current
    DESCRIPTION
    "EX2-DO13 output state when alarm happen
    0:NO;
    1:NC
    "
    ::= { digitalInputAndOutputParameter 35 }
    -- 1.3.6.1.4.1.39553.10.3.10.36
    ex2DO14AlarmState OBJECT-TYPE
    SYNTAX INTEGER {
    no(0),
    nc(1)
    }
    MAX-ACCESS read-write
    STATUS current
    DESCRIPTION
    "EX2-DO14 output state when alarm happen
    0:NO;
    1:NC
    "
    ::= { digitalInputAndOutputParameter 36 }
    -- 1.3.6.1.4.1.39553.10.3.10.37
    ex2DO15AlarmState OBJECT-TYPE
    SYNTAX INTEGER {
    no(0),
    nc(1)
    }
    MAX-ACCESS read-write
    STATUS current
    DESCRIPTION
    "EX2-DO15 output state when alarm happen
    0:NO;
    1:NC
    "
    ::= { digitalInputAndOutputParameter 37 }
    -- 1.3.6.1.4.1.39553.10.3.10.38
    ex2DO16AlarmState OBJECT-TYPE
    SYNTAX INTEGER {
    no(0),
    nc(1)
    }
    MAX-ACCESS read-write
    STATUS current
    DESCRIPTION
    "EX2-DO16 output state when alarm happen
    0:NO;
    1:NC
    "
    ::= { digitalInputAndOutputParameter 38 }
    -- 1.3.6.1.4.1.39553.10.3.10.39
    ex3DO1AlarmState OBJECT-TYPE
    SYNTAX INTEGER {
    no(0),
    nc(1)
    }
    MAX-ACCESS read-write
    STATUS current
    DESCRIPTION
    "EX3-DO1 output state when alarm happen
    0:NO;
    1:NC
    "
    ::= { digitalInputAndOutputParameter 39 }
    -- 1.3.6.1.4.1.39553.10.3.10.40
    ex3DO2AlarmState OBJECT-TYPE
    SYNTAX INTEGER {
    no(0),
    nc(1)
    }
    MAX-ACCESS read-write
    STATUS current
    DESCRIPTION
    "EX3-DO2 output state when alarm happen
    0:NO;
    1:NC
    "
    ::= { digitalInputAndOutputParameter 40 }
    -- 1.3.6.1.4.1.39553.10.3.10.41
    ex3DO3AlarmState OBJECT-TYPE
    SYNTAX INTEGER {
    no(0),
    nc(1)
    }
    MAX-ACCESS read-write
    STATUS current
    DESCRIPTION
    "EX3-DO3 output state when alarm happen
    0:NO;
    1:NC
    "
    ::= { digitalInputAndOutputParameter 41 }
    -- 1.3.6.1.4.1.39553.10.3.10.42
    ex3DO4AlarmState OBJECT-TYPE
    SYNTAX INTEGER {
    no(0),
    nc(1)
    }
    MAX-ACCESS read-write
    STATUS current
    DESCRIPTION
    "EX3-DO4 output state when alarm happen
    0:NO;
    1:NC
    "
    ::= { digitalInputAndOutputParameter 42 }
    -- 1.3.6.1.4.1.39553.10.3.10.43
    ex3DO5AlarmState OBJECT-TYPE
    SYNTAX INTEGER {
    no(0),
    nc(1)
    }
    MAX-ACCESS read-write
    STATUS current
    DESCRIPTION
    "EX3-DO5 output state when alarm happen
    0:NO;
    1:NC
    "
    ::= { digitalInputAndOutputParameter 43 }
    -- 1.3.6.1.4.1.39553.10.3.10.44
    ex3DO6AlarmState OBJECT-TYPE
    SYNTAX INTEGER {
    no(0),
    nc(1)
    }
    MAX-ACCESS read-write
    STATUS current
    DESCRIPTION
    "EX3-DO6 output state when alarm happen
    0:NO;
    1:NC
    "
    ::= { digitalInputAndOutputParameter 44 }
    -- 1.3.6.1.4.1.39553.10.3.10.45
    ex3DO7AlarmState OBJECT-TYPE
    SYNTAX INTEGER {
    no(0),
    nc(1)
    }
    MAX-ACCESS read-write
    STATUS current
    DESCRIPTION
    "EX3-DO7 output state when alarm happen
    0:NO;
    1:NC
    "
    ::= { digitalInputAndOutputParameter 45 }
    -- 1.3.6.1.4.1.39553.10.3.10.46
    ex3DO8AlarmState OBJECT-TYPE
    SYNTAX INTEGER {
    no(0),
    nc(1)
    }
    MAX-ACCESS read-write
    STATUS current
    DESCRIPTION
    "EX3-DO8 output state when alarm happen
    0:NO;
    1:NC
    "
    ::= { digitalInputAndOutputParameter 46 }
    -- 1.3.6.1.4.1.39553.10.3.10.47
    ex3DO9AlarmState OBJECT-TYPE
    SYNTAX INTEGER {
    no(0),
    nc(1)
    }
    MAX-ACCESS read-write
    STATUS current
    DESCRIPTION
    "EX3-DO9 output state when alarm happen
    0:NO;
    1:NC
    "
    ::= { digitalInputAndOutputParameter 47 }
    -- 1.3.6.1.4.1.39553.10.3.10.48
    ex3DO10AlarmState OBJECT-TYPE
    SYNTAX INTEGER {
    no(0),
    nc(1)
    }
    MAX-ACCESS read-write
    STATUS current
    DESCRIPTION
    "EX3-DO10 output state when alarm happen
    0:NO;
    1:NC
    "
    ::= { digitalInputAndOutputParameter 48 }
    -- 1.3.6.1.4.1.39553.10.3.10.49
    ex3DO11AlarmState OBJECT-TYPE
    SYNTAX INTEGER {
    no(0),
    nc(1)
    }
    MAX-ACCESS read-write
    STATUS current
    DESCRIPTION
    "EX3-DO11 output state when alarm happen
    0:NO;
    1:NC
    "
    ::= { digitalInputAndOutputParameter 49 }
    -- 1.3.6.1.4.1.39553.10.3.10.50
    ex3DO12AlarmState OBJECT-TYPE
    SYNTAX INTEGER {
    no(0),
    nc(1)
    }
    MAX-ACCESS read-write
    STATUS current
    DESCRIPTION
    "EX3-DO12 output state when alarm happen
    0:NO;
    1:NC
    "
    ::= { digitalInputAndOutputParameter 50 }
    -- 1.3.6.1.4.1.39553.10.3.10.51
    ex3DO13AlarmState OBJECT-TYPE
    SYNTAX INTEGER {
    no(0),
    nc(1)
    }
    MAX-ACCESS read-write
    STATUS current
    DESCRIPTION
    "EX3-DO13 output state when alarm happen
    0:NO;
    1:NC
    "
    ::= { digitalInputAndOutputParameter 51 }
    -- 1.3.6.1.4.1.39553.10.3.10.52
    ex3DO14AlarmState OBJECT-TYPE
    SYNTAX INTEGER {
    no(0),
    nc(1)
    }
    MAX-ACCESS read-write
    STATUS current
    DESCRIPTION
    "EX3-DO14 output state when alarm happen
    0:NO;
    1:NC
    "
    ::= { digitalInputAndOutputParameter 52 }
    -- 1.3.6.1.4.1.39553.10.3.10.53
    ex3DO15AlarmState OBJECT-TYPE
    SYNTAX INTEGER {
    no(0),
    nc(1)
    }
    MAX-ACCESS read-write
    STATUS current
    DESCRIPTION
    "EX3-DO15 output state when alarm happen
    0:NO;
    1:NC
    "
    ::= { digitalInputAndOutputParameter 53 }
    -- 1.3.6.1.4.1.39553.10.3.10.54
    ex3DO16AlarmState OBJECT-TYPE
    SYNTAX INTEGER {
    no(0),
    nc(1)
    }
    MAX-ACCESS read-write
    STATUS current
    DESCRIPTION
    "EX3-DO16 output state when alarm happen
    0:NO;
    1:NC
    "
    ::= { digitalInputAndOutputParameter 54 }
    -- 1.3.6.1.4.1.39553.10.3.10.55
    ex4DO1AlarmState OBJECT-TYPE
    SYNTAX INTEGER {
    no(0),
    nc(1)
    }
    MAX-ACCESS read-write
    STATUS current
    DESCRIPTION
    "EX4-DO1 output state when alarm happen
    0:NO;
    1:NC
    "
    ::= { digitalInputAndOutputParameter 55 }
    -- 1.3.6.1.4.1.39553.10.3.10.56
    ex4DO2AlarmState OBJECT-TYPE
    SYNTAX INTEGER {
    no(0),
    nc(1)
    }
    MAX-ACCESS read-write
    STATUS current
    DESCRIPTION
    "EX4-DO2 output state when alarm happen
    0:NO;
    1:NC
    "
    ::= { digitalInputAndOutputParameter 56 }
    -- 1.3.6.1.4.1.39553.10.3.10.57
    ex4DO3AlarmState OBJECT-TYPE
    SYNTAX INTEGER {
    no(0),
    nc(1)
    }
    MAX-ACCESS read-write
    STATUS current
    DESCRIPTION
    "EX4-DO3 output state when alarm happen
    0:NO;
    1:NC
    "
    ::= { digitalInputAndOutputParameter 57 }
    -- 1.3.6.1.4.1.39553.10.3.10.58
    ex4DO4AlarmState OBJECT-TYPE
    SYNTAX INTEGER {
    no(0),
    nc(1)
    }
    MAX-ACCESS read-write
    STATUS current
    DESCRIPTION
    "EX4-DO4 output state when alarm happen
    0:NO;
    1:NC
    "
    ::= { digitalInputAndOutputParameter 58 }
    -- 1.3.6.1.4.1.39553.10.3.10.59
    ex4DO5AlarmState OBJECT-TYPE
    SYNTAX INTEGER {
    no(0),
    nc(1)
    }
    MAX-ACCESS read-write
    STATUS current
    DESCRIPTION
    "EX4-DO5 output state when alarm happen
    0:NO;
    1:NC
    "
    ::= { digitalInputAndOutputParameter 59 }
    -- 1.3.6.1.4.1.39553.10.3.10.60
    ex4DO6AlarmState OBJECT-TYPE
    SYNTAX INTEGER {
    no(0),
    nc(1)
    }
    MAX-ACCESS read-write
    STATUS current
    DESCRIPTION
    "EX4-DO6 output state when alarm happen
    0:NO;
    1:NC
    "
    ::= { digitalInputAndOutputParameter 60 }
    -- 1.3.6.1.4.1.39553.10.3.10.61
    ex4DO7AlarmState OBJECT-TYPE
    SYNTAX INTEGER {
    no(0),
    nc(1)
    }
    MAX-ACCESS read-write
    STATUS current
    DESCRIPTION
    "EX4-DO7 output state when alarm happen
    0:NO;
    1:NC
    "
    ::= { digitalInputAndOutputParameter 61 }
    -- 1.3.6.1.4.1.39553.10.3.10.62
    ex4DO8AlarmState OBJECT-TYPE
    SYNTAX INTEGER {
    no(0),
    nc(1)
    }
    MAX-ACCESS read-write
    STATUS current
    DESCRIPTION
    "EX4-DO8 output state when alarm happen
    0:NO;
    1:NC
    "
    ::= { digitalInputAndOutputParameter 62 }
    -- 1.3.6.1.4.1.39553.10.3.10.63
    ex4DO9AlarmState OBJECT-TYPE
    SYNTAX INTEGER {
    no(0),
    nc(1)
    }
    MAX-ACCESS read-write
    STATUS current
    DESCRIPTION
    "EX4-DO9 output state when alarm happen
    0:NO;
    1:NC
    "
    ::= { digitalInputAndOutputParameter 63 }
    -- 1.3.6.1.4.1.39553.10.3.10.64
    ex4DO10AlarmState OBJECT-TYPE
    SYNTAX INTEGER {
    no(0),
    nc(1)
    }
    MAX-ACCESS read-write
    STATUS current
    DESCRIPTION
    "EX4-DO10 output state when alarm happen
    0:NO;
    1:NC
    "
    ::= { digitalInputAndOutputParameter 64 }
    -- 1.3.6.1.4.1.39553.10.3.10.65
    ex4DO11AlarmState OBJECT-TYPE
    SYNTAX INTEGER {
    no(0),
    nc(1)
    }
    MAX-ACCESS read-write
    STATUS current
    DESCRIPTION
    "EX4-DO11 output state when alarm happen
    0:NO;
    1:NC
    "
    ::= { digitalInputAndOutputParameter 65 }
    -- 1.3.6.1.4.1.39553.10.3.10.66
    ex4DO12AlarmState OBJECT-TYPE
    SYNTAX INTEGER {
    no(0),
    nc(1)
    }
    MAX-ACCESS read-write
    STATUS current
    DESCRIPTION
    "EX4-DO12 output state when alarm happen
    0:NO;
    1:NC
    "
    ::= { digitalInputAndOutputParameter 66 }
    -- 1.3.6.1.4.1.39553.10.3.10.67
    ex4DO13AlarmState OBJECT-TYPE
    SYNTAX INTEGER {
    no(0),
    nc(1)
    }
    MAX-ACCESS read-write
    STATUS current
    DESCRIPTION
    "EX4-DO13 output state when alarm happen
    0:NO;
    1:NC
    "
    ::= { digitalInputAndOutputParameter 67 }
    -- 1.3.6.1.4.1.39553.10.3.10.68
    ex4DO14AlarmState OBJECT-TYPE
    SYNTAX INTEGER {
    no(0),
    nc(1)
    }
    MAX-ACCESS read-write
    STATUS current
    DESCRIPTION
    "EX4-DO14 output state when alarm happen
    0:NO;
    1:NC
    "
    ::= { digitalInputAndOutputParameter 68 }
    -- 1.3.6.1.4.1.39553.10.3.10.69
    ex4DO15AlarmState OBJECT-TYPE
    SYNTAX INTEGER {
    no(0),
    nc(1)
    }
    MAX-ACCESS read-write
    STATUS current
    DESCRIPTION
    "EX4-DO15 output state when alarm happen
    0:NO;
    1:NC
    "
    ::= { digitalInputAndOutputParameter 69 }
    -- 1.3.6.1.4.1.39553.10.3.10.70
    ex4DO16AlarmState OBJECT-TYPE
    SYNTAX INTEGER {
    no(0),
    nc(1)
    }
    MAX-ACCESS read-write
    STATUS current
    DESCRIPTION
    "EX4-DO16 output state when alarm happen
    0:NO;
    1:NC
    "
    ::= { digitalInputAndOutputParameter 70 }
    -- 1.3.6.1.4.1.39553.10.3.10.71
    ex5DO1AlarmState OBJECT-TYPE
    SYNTAX INTEGER {
    no(0),
    nc(1)
    }
    MAX-ACCESS read-write
    STATUS current
    DESCRIPTION
    "EX5-DO1 output state when alarm happen
    0:NO;
    1:NC
    "
    ::= { digitalInputAndOutputParameter 71 }
    -- 1.3.6.1.4.1.39553.10.3.10.72
    ex5DO2AlarmState OBJECT-TYPE
    SYNTAX INTEGER {
    no(0),
    nc(1)
    }
    MAX-ACCESS read-write
    STATUS current
    DESCRIPTION
    "EX5-DO2 output state when alarm happen
    0:NO;
    1:NC
    "
    ::= { digitalInputAndOutputParameter 72 }
    -- 1.3.6.1.4.1.39553.10.3.10.73
    ex5DO3AlarmState OBJECT-TYPE
    SYNTAX INTEGER {
    no(0),
    nc(1)
    }
    MAX-ACCESS read-write
    STATUS current
    DESCRIPTION
    "EX5-DO3 output state when alarm happen
    0:NO;
    1:NC
    "
    ::= { digitalInputAndOutputParameter 73 }
    -- 1.3.6.1.4.1.39553.10.3.10.74
    ex5DO4AlarmState OBJECT-TYPE
    SYNTAX INTEGER {
    no(0),
    nc(1)
    }
    MAX-ACCESS read-write
    STATUS current
    DESCRIPTION
    "EX5-DO4 output state when alarm happen
    0:NO;
    1:NC
    "
    ::= { digitalInputAndOutputParameter 74 }
    -- 1.3.6.1.4.1.39553.10.3.10.75
    ex5DO5AlarmState OBJECT-TYPE
    SYNTAX INTEGER {
    no(0),
    nc(1)
    }
    MAX-ACCESS read-write
    STATUS current
    DESCRIPTION
    "EX5-DO5 output state when alarm happen
    0:NO;
    1:NC
    "
    ::= { digitalInputAndOutputParameter 75 }
    -- 1.3.6.1.4.1.39553.10.3.10.76
    ex5DO6AlarmState OBJECT-TYPE
    SYNTAX INTEGER {
    no(0),
    nc(1)
    }
    MAX-ACCESS read-write
    STATUS current
    DESCRIPTION
    "EX5-DO6 output state when alarm happen
    0:NO;
    1:NC
    "
    ::= { digitalInputAndOutputParameter 76 }
    -- 1.3.6.1.4.1.39553.10.3.10.77
    ex5DO7AlarmState OBJECT-TYPE
    SYNTAX INTEGER {
    no(0),
    nc(1)
    }
    MAX-ACCESS read-write
    STATUS current
    DESCRIPTION
    "EX5-DO7 output state when alarm happen
    0:NO;
    1:NC
    "
    ::= { digitalInputAndOutputParameter 77 }
    -- 1.3.6.1.4.1.39553.10.3.10.78
    ex5DO8AlarmState OBJECT-TYPE
    SYNTAX INTEGER {
    no(0),
    nc(1)
    }
    MAX-ACCESS read-write
    STATUS current
    DESCRIPTION
    "EX5-DO8 output state when alarm happen
    0:NO;
    1:NC
    "
    ::= { digitalInputAndOutputParameter 78 }
    -- 1.3.6.1.4.1.39553.10.3.10.79
    ex5DO9AlarmState OBJECT-TYPE
    SYNTAX INTEGER {
    no(0),
    nc(1)
    }
    MAX-ACCESS read-write
    STATUS current
    DESCRIPTION
    "EX5-DO9 output state when alarm happen
    0:NO;
    1:NC
    "
    ::= { digitalInputAndOutputParameter 79 }
    -- 1.3.6.1.4.1.39553.10.3.10.80
    ex5DO10AlarmState OBJECT-TYPE
    SYNTAX INTEGER {
    no(0),
    nc(1)
    }
    MAX-ACCESS read-write
    STATUS current
    DESCRIPTION
    "EX5-DO10 output state when alarm happen
    0:NO;
    1:NC
    "
    ::= { digitalInputAndOutputParameter 80 }
    -- 1.3.6.1.4.1.39553.10.3.10.81
    ex5DO11AlarmState OBJECT-TYPE
    SYNTAX INTEGER {
    no(0),
    nc(1)
    }
    MAX-ACCESS read-write
    STATUS current
    DESCRIPTION
    "EX5-DO11 output state when alarm happen
    0:NO;
    1:NC
    "
    ::= { digitalInputAndOutputParameter 81 }
    -- 1.3.6.1.4.1.39553.10.3.10.82
    ex5DO12AlarmState OBJECT-TYPE
    SYNTAX INTEGER {
    no(0),
    nc(1)
    }
    MAX-ACCESS read-write
    STATUS current
    DESCRIPTION
    "EX5-DO12 output state when alarm happen
    0:NO;
    1:NC
    "
    ::= { digitalInputAndOutputParameter 82 }
    -- 1.3.6.1.4.1.39553.10.3.10.83
    ex5DO13AlarmState OBJECT-TYPE
    SYNTAX INTEGER {
    no(0),
    nc(1)
    }
    MAX-ACCESS read-write
    STATUS current
    DESCRIPTION
    "EX5-DO13 output state when alarm happen
    0:NO;
    1:NC
    "
    ::= { digitalInputAndOutputParameter 83 }
    -- 1.3.6.1.4.1.39553.10.3.10.84
    ex5DO14AlarmState OBJECT-TYPE
    SYNTAX INTEGER {
    no(0),
    nc(1)
    }
    MAX-ACCESS read-write
    STATUS current
    DESCRIPTION
    "EX5-DO14 output state when alarm happen
    0:NO;
    1:NC
    "
    ::= { digitalInputAndOutputParameter 84 }
    -- 1.3.6.1.4.1.39553.10.3.10.85
    ex5DO15AlarmState OBJECT-TYPE
    SYNTAX INTEGER {
    no(0),
    nc(1)
    }
    MAX-ACCESS read-write
    STATUS current
    DESCRIPTION
    "EX5-DO15 output state when alarm happen
    0:NO;
    1:NC
    "
    ::= { digitalInputAndOutputParameter 85 }
    -- 1.3.6.1.4.1.39553.10.3.10.86
    ex5DO16AlarmState OBJECT-TYPE
    SYNTAX INTEGER {
    no(0),
    nc(1)
    }
    MAX-ACCESS read-write
    STATUS current
    DESCRIPTION
    "EX5-DO16 output state when alarm happen
    0:NO;
    1:NC
    "
    ::= { digitalInputAndOutputParameter 86 }
    -- 1.3.6.1.4.1.39553.10.3.10.101
    do1Name OBJECT-TYPE
    SYNTAX DisplayString (SIZE(0..19))
    MAX-ACCESS read-write
    STATUS current
    DESCRIPTION
    "DO1 name setting"
    ::= { digitalInputAndOutputParameter 101 }
    -- 1.3.6.1.4.1.39553.10.3.10.102
    do2Name OBJECT-TYPE
    SYNTAX DisplayString (SIZE(0..19))
    MAX-ACCESS read-write
    STATUS current
    DESCRIPTION
    "DO2 name setting"
    ::= { digitalInputAndOutputParameter 102 }
    -- 1.3.6.1.4.1.39553.10.3.10.103
    do3Name OBJECT-TYPE
    SYNTAX DisplayString (SIZE(0..19))
    MAX-ACCESS read-write
    STATUS current
    DESCRIPTION
    "DO3 name setting"
    ::= { digitalInputAndOutputParameter 103 }
    -- 1.3.6.1.4.1.39553.10.3.10.104
    do4Name OBJECT-TYPE
    SYNTAX DisplayString (SIZE(0..19))
    MAX-ACCESS read-write
    STATUS current
    DESCRIPTION
    "DO4 name setting"
    ::= { digitalInputAndOutputParameter 104 }
    -- 1.3.6.1.4.1.39553.10.3.10.105
    do5Name OBJECT-TYPE
    SYNTAX DisplayString (SIZE(0..19))
    MAX-ACCESS read-write
    STATUS current
    DESCRIPTION
    "DO5 name setting"
    ::= { digitalInputAndOutputParameter 105 }
    -- 1.3.6.1.4.1.39553.10.3.10.106
    do6Name OBJECT-TYPE
    SYNTAX DisplayString (SIZE(0..19))
    MAX-ACCESS read-write
    STATUS current
    DESCRIPTION
    "DO6 name setting"
    ::= { digitalInputAndOutputParameter 106 }
    -- 1.3.6.1.4.1.39553.10.3.10.107
    ex1DO1Name OBJECT-TYPE
    SYNTAX DisplayString (SIZE(0..19))
    MAX-ACCESS read-write
    STATUS current
    DESCRIPTION
    "EX1-DO1 name setting"
    ::= { digitalInputAndOutputParameter 107 }
    -- 1.3.6.1.4.1.39553.10.3.10.108
    ex1DO2Name OBJECT-TYPE
    SYNTAX DisplayString (SIZE(0..19))
    MAX-ACCESS read-write
    STATUS current
    DESCRIPTION
    "EX1-DO2 name setting"
    ::= { digitalInputAndOutputParameter 108 }
    -- 1.3.6.1.4.1.39553.10.3.10.109
    ex1DO3Name OBJECT-TYPE
    SYNTAX DisplayString (SIZE(0..19))
    MAX-ACCESS read-write
    STATUS current
    DESCRIPTION
    "EX1-DO3 name setting"
    ::= { digitalInputAndOutputParameter 109 }
    -- 1.3.6.1.4.1.39553.10.3.10.110
    ex1DO4Name OBJECT-TYPE
    SYNTAX DisplayString (SIZE(0..19))
    MAX-ACCESS read-write
    STATUS current
    DESCRIPTION
    "EX1-DO4 name setting"
    ::= { digitalInputAndOutputParameter 110 }
    -- 1.3.6.1.4.1.39553.10.3.10.111
    ex1DO5Name OBJECT-TYPE
    SYNTAX DisplayString (SIZE(0..19))
    MAX-ACCESS read-write
    STATUS current
    DESCRIPTION
    "EX1-DO5 name setting"
    ::= { digitalInputAndOutputParameter 111 }
    -- 1.3.6.1.4.1.39553.10.3.10.112
    ex1DO6Name OBJECT-TYPE
    SYNTAX DisplayString (SIZE(0..19))
    MAX-ACCESS read-write
    STATUS current
    DESCRIPTION
    "EX1-DO6 name setting"
    ::= { digitalInputAndOutputParameter 112 }
    -- 1.3.6.1.4.1.39553.10.3.10.113
    ex1DO7Name OBJECT-TYPE
    SYNTAX DisplayString (SIZE(0..19))
    MAX-ACCESS read-write
    STATUS current
    DESCRIPTION
    "EX1-DO7 name setting"
    ::= { digitalInputAndOutputParameter 113 }
    -- 1.3.6.1.4.1.39553.10.3.10.114
    ex1DO8Name OBJECT-TYPE
    SYNTAX DisplayString (SIZE(0..19))
    MAX-ACCESS read-write
    STATUS current
    DESCRIPTION
    "EX1-DO8 name setting"
    ::= { digitalInputAndOutputParameter 114 }
    -- 1.3.6.1.4.1.39553.10.3.10.115
    ex1DO9Name OBJECT-TYPE
    SYNTAX DisplayString (SIZE(0..19))
    MAX-ACCESS read-write
    STATUS current
    DESCRIPTION
    "EX1-DO9 name setting"
    ::= { digitalInputAndOutputParameter 115 }
    -- 1.3.6.1.4.1.39553.10.3.10.116
    ex1DO10Name OBJECT-TYPE
    SYNTAX DisplayString (SIZE(0..19))
    MAX-ACCESS read-write
    STATUS current
    DESCRIPTION
    "EX1-DO10 name setting"
    ::= { digitalInputAndOutputParameter 116 }
    -- 1.3.6.1.4.1.39553.10.3.10.117
    ex1DO11Name OBJECT-TYPE
    SYNTAX DisplayString (SIZE(0..19))
    MAX-ACCESS read-write
    STATUS current
    DESCRIPTION
    "EX1-DO11 name setting"
    ::= { digitalInputAndOutputParameter 117 }
    -- 1.3.6.1.4.1.39553.10.3.10.118
    ex1DO12Name OBJECT-TYPE
    SYNTAX DisplayString (SIZE(0..19))
    MAX-ACCESS read-write
    STATUS current
    DESCRIPTION
    "EX1-DO12 name setting"
    ::= { digitalInputAndOutputParameter 118 }
    -- 1.3.6.1.4.1.39553.10.3.10.119
    ex1DO13Name OBJECT-TYPE
    SYNTAX DisplayString (SIZE(0..19))
    MAX-ACCESS read-write
    STATUS current
    DESCRIPTION
    "EX1-DO13 name setting"
    ::= { digitalInputAndOutputParameter 119 }
    -- 1.3.6.1.4.1.39553.10.3.10.120
    ex1DO14Name OBJECT-TYPE
    SYNTAX DisplayString (SIZE(0..19))
    MAX-ACCESS read-write
    STATUS current
    DESCRIPTION
    "EX1-DO14 name setting"
    ::= { digitalInputAndOutputParameter 120 }
    -- 1.3.6.1.4.1.39553.10.3.10.121
    ex1DO15Name OBJECT-TYPE
    SYNTAX DisplayString (SIZE(0..19))
    MAX-ACCESS read-write
    STATUS current
    DESCRIPTION
    "EX1-DO15 name setting"
    ::= { digitalInputAndOutputParameter 121 }
    -- 1.3.6.1.4.1.39553.10.3.10.122
    ex1DO16Name OBJECT-TYPE
    SYNTAX DisplayString (SIZE(0..19))
    MAX-ACCESS read-write
    STATUS current
    DESCRIPTION
    "EX1-DO16 name setting"
    ::= { digitalInputAndOutputParameter 122 }
    -- 1.3.6.1.4.1.39553.10.3.10.123
    ex2DO1Name OBJECT-TYPE
    SYNTAX DisplayString (SIZE(0..19))
    MAX-ACCESS read-write
    STATUS current
    DESCRIPTION
    "EX2-DO1 name setting"
    ::= { digitalInputAndOutputParameter 123 }
    -- 1.3.6.1.4.1.39553.10.3.10.124
    ex2DO2Name OBJECT-TYPE
    SYNTAX DisplayString (SIZE(0..19))
    MAX-ACCESS read-write
    STATUS current
    DESCRIPTION
    "EX2-DO2 name setting"
    ::= { digitalInputAndOutputParameter 124 }
    -- 1.3.6.1.4.1.39553.10.3.10.125
    ex2DO3Name OBJECT-TYPE
    SYNTAX DisplayString (SIZE(0..19))
    MAX-ACCESS read-write
    STATUS current
    DESCRIPTION
    "EX2-DO3 name setting"
    ::= { digitalInputAndOutputParameter 125 }
    -- 1.3.6.1.4.1.39553.10.3.10.126
    ex2DO4Name OBJECT-TYPE
    SYNTAX DisplayString (SIZE(0..19))
    MAX-ACCESS read-write
    STATUS current
    DESCRIPTION
    "EX2-DO4 name setting"
    ::= { digitalInputAndOutputParameter 126 }
    -- 1.3.6.1.4.1.39553.10.3.10.127
    ex2DO5Name OBJECT-TYPE
    SYNTAX DisplayString (SIZE(0..19))
    MAX-ACCESS read-write
    STATUS current
    DESCRIPTION
    "EX2-DO5 name setting"
    ::= { digitalInputAndOutputParameter 127 }
    -- 1.3.6.1.4.1.39553.10.3.10.128
    ex2DO6Name OBJECT-TYPE
    SYNTAX DisplayString (SIZE(0..19))
    MAX-ACCESS read-write
    STATUS current
    DESCRIPTION
    "EX2-DO6 name setting"
    ::= { digitalInputAndOutputParameter 128 }
    -- 1.3.6.1.4.1.39553.10.3.10.129
    ex2DO7Name OBJECT-TYPE
    SYNTAX DisplayString (SIZE(0..19))
    MAX-ACCESS read-write
    STATUS current
    DESCRIPTION
    "EX2-DO7 name setting"
    ::= { digitalInputAndOutputParameter 129 }
    -- 1.3.6.1.4.1.39553.10.3.10.130
    ex2DO8Name OBJECT-TYPE
    SYNTAX DisplayString (SIZE(0..19))
    MAX-ACCESS read-write
    STATUS current
    DESCRIPTION
    "EX2-DO8 name setting"
    ::= { digitalInputAndOutputParameter 130 }
    -- 1.3.6.1.4.1.39553.10.3.10.131
    ex2DO9Name OBJECT-TYPE
    SYNTAX DisplayString (SIZE(0..19))
    MAX-ACCESS read-write
    STATUS current
    DESCRIPTION
    "EX2-DO9 name setting"
    ::= { digitalInputAndOutputParameter 131 }
    -- 1.3.6.1.4.1.39553.10.3.10.132
    ex2DO10Name OBJECT-TYPE
    SYNTAX DisplayString (SIZE(0..19))
    MAX-ACCESS read-write
    STATUS current
    DESCRIPTION
    "EX2-DO10 name setting"
    ::= { digitalInputAndOutputParameter 132 }
    -- 1.3.6.1.4.1.39553.10.3.10.133
    ex2DO11Name OBJECT-TYPE
    SYNTAX DisplayString (SIZE(0..19))
    MAX-ACCESS read-write
    STATUS current
    DESCRIPTION
    "EX2-DO11 name setting"
    ::= { digitalInputAndOutputParameter 133 }
    -- 1.3.6.1.4.1.39553.10.3.10.134
    ex2DO12Name OBJECT-TYPE
    SYNTAX DisplayString (SIZE(0..19))
    MAX-ACCESS read-write
    STATUS current
    DESCRIPTION
    "EX2-DO12 name setting"
    ::= { digitalInputAndOutputParameter 134 }
    -- 1.3.6.1.4.1.39553.10.3.10.135
    ex2DO13Name OBJECT-TYPE
    SYNTAX DisplayString (SIZE(0..19))
    MAX-ACCESS read-write
    STATUS current
    DESCRIPTION
    "EX2-DO13 name setting"
    ::= { digitalInputAndOutputParameter 135 }
    -- 1.3.6.1.4.1.39553.10.3.10.136
    ex2DO14Name OBJECT-TYPE
    SYNTAX DisplayString (SIZE(0..19))
    MAX-ACCESS read-write
    STATUS current
    DESCRIPTION
    "EX2-DO14 name setting"
    ::= { digitalInputAndOutputParameter 136 }
    -- 1.3.6.1.4.1.39553.10.3.10.137
    ex2DO15Name OBJECT-TYPE
    SYNTAX DisplayString (SIZE(0..19))
    MAX-ACCESS read-write
    STATUS current
    DESCRIPTION
    "EX2-DO15 name setting"
    ::= { digitalInputAndOutputParameter 137 }
    -- 1.3.6.1.4.1.39553.10.3.10.138
    ex2DO16Name OBJECT-TYPE
    SYNTAX DisplayString (SIZE(0..19))
    MAX-ACCESS read-write
    STATUS current
    DESCRIPTION
    "EX2-DO16 name setting"
    ::= { digitalInputAndOutputParameter 138 }
    -- 1.3.6.1.4.1.39553.10.3.10.139
    ex3DO1Name OBJECT-TYPE
    SYNTAX DisplayString (SIZE(0..19))
    MAX-ACCESS read-write
    STATUS current
    DESCRIPTION
    "EX3-DO1 name setting"
    ::= { digitalInputAndOutputParameter 139 }
    -- 1.3.6.1.4.1.39553.10.3.10.140
    ex3DO2Name OBJECT-TYPE
    SYNTAX DisplayString (SIZE(0..19))
    MAX-ACCESS read-write
    STATUS current
    DESCRIPTION
    "EX3-DO2 name setting"
    ::= { digitalInputAndOutputParameter 140 }
    -- 1.3.6.1.4.1.39553.10.3.10.141
    ex3DO3Name OBJECT-TYPE
    SYNTAX DisplayString (SIZE(0..19))
    MAX-ACCESS read-write
    STATUS current
    DESCRIPTION
    "EX3-DO3 name setting"
    ::= { digitalInputAndOutputParameter 141 }
    -- 1.3.6.1.4.1.39553.10.3.10.142
    ex3DO4Name OBJECT-TYPE
    SYNTAX DisplayString (SIZE(0..19))
    MAX-ACCESS read-write
    STATUS current
    DESCRIPTION
    "EX3-DO4 name setting"
    ::= { digitalInputAndOutputParameter 142 }
    -- 1.3.6.1.4.1.39553.10.3.10.143
    ex3DO5Name OBJECT-TYPE
    SYNTAX DisplayString (SIZE(0..19))
    MAX-ACCESS read-write
    STATUS current
    DESCRIPTION
    "EX3-DO5 name setting"
    ::= { digitalInputAndOutputParameter 143 }
    -- 1.3.6.1.4.1.39553.10.3.10.144
    ex3DO6Name OBJECT-TYPE
    SYNTAX DisplayString (SIZE(0..19))
    MAX-ACCESS read-write
    STATUS current
    DESCRIPTION
    "EX3-DO6 name setting"
    ::= { digitalInputAndOutputParameter 144 }
    -- 1.3.6.1.4.1.39553.10.3.10.145
    ex3DO7Name OBJECT-TYPE
    SYNTAX DisplayString (SIZE(0..19))
    MAX-ACCESS read-write
    STATUS current
    DESCRIPTION
    "EX3-DO7 name setting"
    ::= { digitalInputAndOutputParameter 145 }
    -- 1.3.6.1.4.1.39553.10.3.10.146
    ex3DO8Name OBJECT-TYPE
    SYNTAX DisplayString (SIZE(0..19))
    MAX-ACCESS read-write
    STATUS current
    DESCRIPTION
    "EX3-DO8 name setting"
    ::= { digitalInputAndOutputParameter 146 }
    -- 1.3.6.1.4.1.39553.10.3.10.147
    ex3DO9Name OBJECT-TYPE
    SYNTAX DisplayString (SIZE(0..19))
    MAX-ACCESS read-write
    STATUS current
    DESCRIPTION
    "EX3-DO9 name setting"
    ::= { digitalInputAndOutputParameter 147 }
    -- 1.3.6.1.4.1.39553.10.3.10.148
    ex3DO10Name OBJECT-TYPE
    SYNTAX DisplayString (SIZE(0..19))
    MAX-ACCESS read-write
    STATUS current
    DESCRIPTION
    "EX3-DO10 name setting"
    ::= { digitalInputAndOutputParameter 148 }
    -- 1.3.6.1.4.1.39553.10.3.10.149
    ex3DO11Name OBJECT-TYPE
    SYNTAX DisplayString (SIZE(0..19))
    MAX-ACCESS read-write
    STATUS current
    DESCRIPTION
    "EX3-DO11 name setting"
    ::= { digitalInputAndOutputParameter 149 }
    -- 1.3.6.1.4.1.39553.10.3.10.150
    ex3DO12Name OBJECT-TYPE
    SYNTAX DisplayString (SIZE(0..19))
    MAX-ACCESS read-write
    STATUS current
    DESCRIPTION
    "EX3-DO12 name setting"
    ::= { digitalInputAndOutputParameter 150 }
    -- 1.3.6.1.4.1.39553.10.3.10.151
    ex3DO13Name OBJECT-TYPE
    SYNTAX DisplayString (SIZE(0..19))
    MAX-ACCESS read-write
    STATUS current
    DESCRIPTION
    "EX3-DO13 name setting"
    ::= { digitalInputAndOutputParameter 151 }
    -- 1.3.6.1.4.1.39553.10.3.10.152
    ex3DO14Name OBJECT-TYPE
    SYNTAX DisplayString (SIZE(0..19))
    MAX-ACCESS read-write
    STATUS current
    DESCRIPTION
    "EX3-DO14 name setting"
    ::= { digitalInputAndOutputParameter 152 }
    -- 1.3.6.1.4.1.39553.10.3.10.153
    ex3DO15Name OBJECT-TYPE
    SYNTAX DisplayString (SIZE(0..19))
    MAX-ACCESS read-write
    STATUS current
    DESCRIPTION
    "EX3-DO15 name setting"
    ::= { digitalInputAndOutputParameter 153 }
    -- 1.3.6.1.4.1.39553.10.3.10.154
    ex3DO16Name OBJECT-TYPE
    SYNTAX DisplayString (SIZE(0..19))
    MAX-ACCESS read-write
    STATUS current
    DESCRIPTION
    "EX3-DO16 name setting"
    ::= { digitalInputAndOutputParameter 154 }
    -- 1.3.6.1.4.1.39553.10.3.10.155
    ex4DO1Name OBJECT-TYPE
    SYNTAX DisplayString (SIZE(0..19))
    MAX-ACCESS read-write
    STATUS current
    DESCRIPTION
    "EX4-DO1 name setting"
    ::= { digitalInputAndOutputParameter 155 }
    -- 1.3.6.1.4.1.39553.10.3.10.156
    ex4DO2Name OBJECT-TYPE
    SYNTAX DisplayString (SIZE(0..19))
    MAX-ACCESS read-write
    STATUS current
    DESCRIPTION
    "EX4-DO2 name setting"
    ::= { digitalInputAndOutputParameter 156 }
    -- 1.3.6.1.4.1.39553.10.3.10.157
    ex4DO3Name OBJECT-TYPE
    SYNTAX DisplayString (SIZE(0..19))
    MAX-ACCESS read-write
    STATUS current
    DESCRIPTION
    "EX4-DO3 name setting"
    ::= { digitalInputAndOutputParameter 157 }
    -- 1.3.6.1.4.1.39553.10.3.10.158
    ex4DO4Name OBJECT-TYPE
    SYNTAX DisplayString (SIZE(0..19))
    MAX-ACCESS read-write
    STATUS current
    DESCRIPTION
    "EX4-DO4 name setting"
    ::= { digitalInputAndOutputParameter 158 }
    -- 1.3.6.1.4.1.39553.10.3.10.159
    ex4DO5Name OBJECT-TYPE
    SYNTAX DisplayString (SIZE(0..19))
    MAX-ACCESS read-write
    STATUS current
    DESCRIPTION
    "EX4-DO5 name setting"
    ::= { digitalInputAndOutputParameter 159 }
    -- 1.3.6.1.4.1.39553.10.3.10.160
    ex4DO6Name OBJECT-TYPE
    SYNTAX DisplayString (SIZE(0..19))
    MAX-ACCESS read-write
    STATUS current
    DESCRIPTION
    "EX4-DO6 name setting"
    ::= { digitalInputAndOutputParameter 160 }
    -- 1.3.6.1.4.1.39553.10.3.10.161
    ex4DO7Name OBJECT-TYPE
    SYNTAX DisplayString (SIZE(0..19))
    MAX-ACCESS read-write
    STATUS current
    DESCRIPTION
    "EX4-DO7 name setting"
    ::= { digitalInputAndOutputParameter 161 }
    -- 1.3.6.1.4.1.39553.10.3.10.162
    ex4DO8Name OBJECT-TYPE
    SYNTAX DisplayString (SIZE(0..19))
    MAX-ACCESS read-write
    STATUS current
    DESCRIPTION
    "EX4-DO8 name setting"
    ::= { digitalInputAndOutputParameter 162 }
    -- 1.3.6.1.4.1.39553.10.3.10.163
    ex4DO9Name OBJECT-TYPE
    SYNTAX DisplayString (SIZE(0..19))
    MAX-ACCESS read-write
    STATUS current
    DESCRIPTION
    "EX4-DO9 name setting"
    ::= { digitalInputAndOutputParameter 163 }
    -- 1.3.6.1.4.1.39553.10.3.10.164
    ex4DO10Name OBJECT-TYPE
    SYNTAX DisplayString (SIZE(0..19))
    MAX-ACCESS read-write
    STATUS current
    DESCRIPTION
    "EX4-DO10 name setting"
    ::= { digitalInputAndOutputParameter 164 }
    -- 1.3.6.1.4.1.39553.10.3.10.165
    ex4DO11Name OBJECT-TYPE
    SYNTAX DisplayString (SIZE(0..19))
    MAX-ACCESS read-write
    STATUS current
    DESCRIPTION
    "EX4-DO11 name setting"
    ::= { digitalInputAndOutputParameter 165 }
    -- 1.3.6.1.4.1.39553.10.3.10.166
    ex4DO12Name OBJECT-TYPE
    SYNTAX DisplayString (SIZE(0..19))
    MAX-ACCESS read-write
    STATUS current
    DESCRIPTION
    "EX4-DO12 name setting"
    ::= { digitalInputAndOutputParameter 166 }
    -- 1.3.6.1.4.1.39553.10.3.10.167
    ex4DO13Name OBJECT-TYPE
    SYNTAX DisplayString (SIZE(0..19))
    MAX-ACCESS read-write
    STATUS current
    DESCRIPTION
    "EX4-DO13 name setting"
    ::= { digitalInputAndOutputParameter 167 }
    -- 1.3.6.1.4.1.39553.10.3.10.168
    ex4DO14Name OBJECT-TYPE
    SYNTAX DisplayString (SIZE(0..19))
    MAX-ACCESS read-write
    STATUS current
    DESCRIPTION
    "EX4-DO14 name setting"
    ::= { digitalInputAndOutputParameter 168 }
    -- 1.3.6.1.4.1.39553.10.3.10.169
    ex4DO15Name OBJECT-TYPE
    SYNTAX DisplayString (SIZE(0..19))
    MAX-ACCESS read-write
    STATUS current
    DESCRIPTION
    "EX4-DO15 name setting"
    ::= { digitalInputAndOutputParameter 169 }
    -- 1.3.6.1.4.1.39553.10.3.10.170
    ex4DO16Name OBJECT-TYPE
    SYNTAX DisplayString (SIZE(0..19))
    MAX-ACCESS read-write
    STATUS current
    DESCRIPTION
    "EX4-DO16 name setting"
    ::= { digitalInputAndOutputParameter 170 }
    -- 1.3.6.1.4.1.39553.10.3.10.171
    ex5DO1Name OBJECT-TYPE
    SYNTAX DisplayString (SIZE(0..19))
    MAX-ACCESS read-write
    STATUS current
    DESCRIPTION
    "EX5-DO1 name setting"
    ::= { digitalInputAndOutputParameter 171 }
    -- 1.3.6.1.4.1.39553.10.3.10.172
    ex5DO2Name OBJECT-TYPE
    SYNTAX DisplayString (SIZE(0..19))
    MAX-ACCESS read-write
    STATUS current
    DESCRIPTION
    "EX5-DO2 name setting"
    ::= { digitalInputAndOutputParameter 172 }
    -- 1.3.6.1.4.1.39553.10.3.10.173
    ex5DO3Name OBJECT-TYPE
    SYNTAX DisplayString (SIZE(0..19))
    MAX-ACCESS read-write
    STATUS current
    DESCRIPTION
    "EX5-DO3 name setting"
    ::= { digitalInputAndOutputParameter 173 }
    -- 1.3.6.1.4.1.39553.10.3.10.174
    ex5DO4Name OBJECT-TYPE
    SYNTAX DisplayString (SIZE(0..19))
    MAX-ACCESS read-write
    STATUS current
    DESCRIPTION
    "EX5-DO4 name setting"
    ::= { digitalInputAndOutputParameter 174 }
    -- 1.3.6.1.4.1.39553.10.3.10.175
    ex5DO5Name OBJECT-TYPE
    SYNTAX DisplayString (SIZE(0..19))
    MAX-ACCESS read-write
    STATUS current
    DESCRIPTION
    "EX5-DO5 name setting"
    ::= { digitalInputAndOutputParameter 175 }
    -- 1.3.6.1.4.1.39553.10.3.10.176
    ex5DO6Name OBJECT-TYPE
    SYNTAX DisplayString (SIZE(0..19))
    MAX-ACCESS read-write
    STATUS current
    DESCRIPTION
    "EX5-DO6 name setting"
    ::= { digitalInputAndOutputParameter 176 }
    -- 1.3.6.1.4.1.39553.10.3.10.177
    ex5DO7Name OBJECT-TYPE
    SYNTAX DisplayString (SIZE(0..19))
    MAX-ACCESS read-write
    STATUS current
    DESCRIPTION
    "EX5-DO7 name setting"
    ::= { digitalInputAndOutputParameter 177 }
    -- 1.3.6.1.4.1.39553.10.3.10.178
    ex5DO8Name OBJECT-TYPE
    SYNTAX DisplayString (SIZE(0..19))
    MAX-ACCESS read-write
    STATUS current
    DESCRIPTION
    "EX5-DO8 name setting"
    ::= { digitalInputAndOutputParameter 178 }
    -- 1.3.6.1.4.1.39553.10.3.10.179
    ex5DO9Name OBJECT-TYPE
    SYNTAX DisplayString (SIZE(0..19))
    MAX-ACCESS read-write
    STATUS current
    DESCRIPTION
    "EX5-DO9 name setting"
    ::= { digitalInputAndOutputParameter 179 }
    -- 1.3.6.1.4.1.39553.10.3.10.180
    ex5DO10Name OBJECT-TYPE
    SYNTAX DisplayString (SIZE(0..19))
    MAX-ACCESS read-write
    STATUS current
    DESCRIPTION
    "EX5-DO10 name setting"
    ::= { digitalInputAndOutputParameter 180 }
    -- 1.3.6.1.4.1.39553.10.3.10.181
    ex5DO11Name OBJECT-TYPE
    SYNTAX DisplayString (SIZE(0..19))
    MAX-ACCESS read-write
    STATUS current
    DESCRIPTION
    "EX5-DO11 name setting"
    ::= { digitalInputAndOutputParameter 181 }
    -- 1.3.6.1.4.1.39553.10.3.10.182
    ex5DO12Name OBJECT-TYPE
    SYNTAX DisplayString (SIZE(0..19))
    MAX-ACCESS read-write
    STATUS current
    DESCRIPTION
    "EX5-DO12 name setting"
    ::= { digitalInputAndOutputParameter 182 }
    -- 1.3.6.1.4.1.39553.10.3.10.183
    ex5DO13Name OBJECT-TYPE
    SYNTAX DisplayString (SIZE(0..19))
    MAX-ACCESS read-write
    STATUS current
    DESCRIPTION
    "EX5-DO13 name setting"
    ::= { digitalInputAndOutputParameter 183 }
    -- 1.3.6.1.4.1.39553.10.3.10.184
    ex5DO14Name OBJECT-TYPE
    SYNTAX DisplayString (SIZE(0..19))
    MAX-ACCESS read-write
    STATUS current
    DESCRIPTION
    "EX5-DO14 name setting"
    ::= { digitalInputAndOutputParameter 184 }
    -- 1.3.6.1.4.1.39553.10.3.10.185
    ex5DO15Name OBJECT-TYPE
    SYNTAX DisplayString (SIZE(0..19))
    MAX-ACCESS read-write
    STATUS current
    DESCRIPTION
    "EX5-DO15 name setting"
    ::= { digitalInputAndOutputParameter 185 }
    -- 1.3.6.1.4.1.39553.10.3.10.186
    ex5DO16Name OBJECT-TYPE
    SYNTAX DisplayString (SIZE(0..19))
    MAX-ACCESS read-write
    STATUS current
    DESCRIPTION
    "EX5-DO16 name setting"
    ::= { digitalInputAndOutputParameter 186 }
    -- 1.3.6.1.4.1.39553.10.3.10.201
    di1Normal OBJECT-TYPE
    SYNTAX INTEGER {
    no(0),
	nc(1)
    }
    MAX-ACCESS read-write
    STATUS current
    DESCRIPTION
    "DI1 input state when normal(no alarm)
    0:NO;
	1:NC
    "
    ::= { digitalInputAndOutputParameter 201 }
    -- 1.3.6.1.4.1.39553.10.3.10.202
    di2Normal OBJECT-TYPE
    SYNTAX INTEGER {
    no(0),
	nc(1)
    }
    MAX-ACCESS read-write
    STATUS current
    DESCRIPTION
    "DI2 input state when normal(no alarm)
    0:NO;
	1:NC
    "
    ::= { digitalInputAndOutputParameter 202 }
    -- 1.3.6.1.4.1.39553.10.3.10.203
    di3Normal OBJECT-TYPE
    SYNTAX INTEGER {
    no(0),
	nc(1)
    }
    MAX-ACCESS read-write
    STATUS current
    DESCRIPTION
    "DI3 input state when normal(no alarm)
    0:NO;
	1:NC
    "
    ::= { digitalInputAndOutputParameter 203 }
    -- 1.3.6.1.4.1.39553.10.3.10.204
    di4Normal OBJECT-TYPE
    SYNTAX INTEGER {
    no(0),
	nc(1)
    }
    MAX-ACCESS read-write
    STATUS current
    DESCRIPTION
    "DI4 input state when normal(no alarm)
    0:NO;
	1:NC
    "
    ::= { digitalInputAndOutputParameter 204 }
    -- 1.3.6.1.4.1.39553.10.3.10.205
    di5Normal OBJECT-TYPE
    SYNTAX INTEGER {
    no(0),
	nc(1)
    }
    MAX-ACCESS read-write
    STATUS current
    DESCRIPTION
    "DI5 input state when normal(no alarm)
    0:NO;
	1:NC
    "
    ::= { digitalInputAndOutputParameter 205 }
    -- 1.3.6.1.4.1.39553.10.3.10.206
    di6Normal OBJECT-TYPE
    SYNTAX INTEGER {
    no(0),
	nc(1)
    }
    MAX-ACCESS read-write
    STATUS current
    DESCRIPTION
    "DI6 input state when normal(no alarm)
    0:NO;
	1:NC
    "
    ::= { digitalInputAndOutputParameter 206 }
    -- 1.3.6.1.4.1.39553.10.3.10.207
    ex1DI1Normal OBJECT-TYPE
    SYNTAX INTEGER {
    no(0),
	nc(1)
    }
    MAX-ACCESS read-write
    STATUS current
    DESCRIPTION
    "EX1-DI1 input state when normal(no alarm)
    0:NO;
	1:NC
    "
    ::= { digitalInputAndOutputParameter 207 }
    -- 1.3.6.1.4.1.39553.10.3.10.208
    ex1DI2Normal OBJECT-TYPE
    SYNTAX INTEGER {
    no(0),
	nc(1)
    }
    MAX-ACCESS read-write
    STATUS current
    DESCRIPTION
    "EX1-DI2 input state when normal(no alarm)
    0:NO;
	1:NC
    "
    ::= { digitalInputAndOutputParameter 208 }
    -- 1.3.6.1.4.1.39553.10.3.10.209
    ex1DI3Normal OBJECT-TYPE
    SYNTAX INTEGER {
    no(0),
	nc(1)
    }
    MAX-ACCESS read-write
    STATUS current
    DESCRIPTION
    "EX1-DI3 input state when normal(no alarm)
    0:NO;
	1:NC
    "
    ::= { digitalInputAndOutputParameter 209 }
    -- 1.3.6.1.4.1.39553.10.3.10.210
    ex1DI4Normal OBJECT-TYPE
    SYNTAX INTEGER {
    no(0),
	nc(1)
    }
    MAX-ACCESS read-write
    STATUS current
    DESCRIPTION
    "EX1-DI4 input state when normal(no alarm)
    0:NO;
	1:NC
    "
    ::= { digitalInputAndOutputParameter 210 }
    -- 1.3.6.1.4.1.39553.10.3.10.211
    ex1DI5Normal OBJECT-TYPE
    SYNTAX INTEGER {
    no(0),
	nc(1)
    }
    MAX-ACCESS read-write
    STATUS current
    DESCRIPTION
    "EX1-DI5 input state when normal(no alarm)
    0:NO;
	1:NC
    "
    ::= { digitalInputAndOutputParameter 211 }
    -- 1.3.6.1.4.1.39553.10.3.10.212
    ex1DI6Normal OBJECT-TYPE
    SYNTAX INTEGER {
    no(0),
	nc(1)
    }
    MAX-ACCESS read-write
    STATUS current
    DESCRIPTION
    "EX1-DI6 input state when normal(no alarm)
    0:NO;
	1:NC
    "
    ::= { digitalInputAndOutputParameter 212 }
    -- 1.3.6.1.4.1.39553.10.3.10.213
    ex1DI7Normal OBJECT-TYPE
    SYNTAX INTEGER {
    no(0),
	nc(1)
    }
    MAX-ACCESS read-write
    STATUS current
    DESCRIPTION
    "EX1-DI7 input state when normal(no alarm)
    0:NO;
	1:NC
    "
    ::= { digitalInputAndOutputParameter 213 }
    -- 1.3.6.1.4.1.39553.10.3.10.214
    ex1DI8Normal OBJECT-TYPE
    SYNTAX INTEGER {
    no(0),
	nc(1)
    }
    MAX-ACCESS read-write
    STATUS current
    DESCRIPTION
    "EX1-DI8 input state when normal(no alarm)
    0:NO;
	1:NC
    "
    ::= { digitalInputAndOutputParameter 214 }
    -- 1.3.6.1.4.1.39553.10.3.10.215
    ex2DI1Normal OBJECT-TYPE
    SYNTAX INTEGER {
    no(0),
	nc(1)
    }
    MAX-ACCESS read-write
    STATUS current
    DESCRIPTION
    "EX2-DI1 input state when normal(no alarm)
    0:NO;
	1:NC
    "
    ::= { digitalInputAndOutputParameter 215 }
    -- 1.3.6.1.4.1.39553.10.3.10.216
    ex2DI2Normal OBJECT-TYPE
    SYNTAX INTEGER {
    no(0),
	nc(1)
    }
    MAX-ACCESS read-write
    STATUS current
    DESCRIPTION
    "EX2-DI2 input state when normal(no alarm)
    0:NO;
	1:NC
    "
    ::= { digitalInputAndOutputParameter 216 }
    -- 1.3.6.1.4.1.39553.10.3.10.217
    ex2DI3Normal OBJECT-TYPE
    SYNTAX INTEGER {
    no(0),
	nc(1)
    }
    MAX-ACCESS read-write
    STATUS current
    DESCRIPTION
    "EX2-DI3 input state when normal(no alarm)
    0:NO;
	1:NC
    "
    ::= { digitalInputAndOutputParameter 217 }
    -- 1.3.6.1.4.1.39553.10.3.10.218
    ex2DI4Normal OBJECT-TYPE
    SYNTAX INTEGER {
    no(0),
	nc(1)
    }
    MAX-ACCESS read-write
    STATUS current
    DESCRIPTION
    "EX2-DI4 input state when normal(no alarm)
    0:NO;
	1:NC
    "
    ::= { digitalInputAndOutputParameter 218 }
    -- 1.3.6.1.4.1.39553.10.3.10.219
    ex2DI5Normal OBJECT-TYPE
    SYNTAX INTEGER {
    no(0),
	nc(1)
    }
    MAX-ACCESS read-write
    STATUS current
    DESCRIPTION
    "EX2-DI5 input state when normal(no alarm)
    0:NO;
	1:NC
    "
    ::= { digitalInputAndOutputParameter 219 }
    -- 1.3.6.1.4.1.39553.10.3.10.220
    ex2DI6Normal OBJECT-TYPE
    SYNTAX INTEGER {
    no(0),
	nc(1)
    }
    MAX-ACCESS read-write
    STATUS current
    DESCRIPTION
    "EX2-DI6 input state when normal(no alarm)
    0:NO;
	1:NC
    "
    ::= { digitalInputAndOutputParameter 220 }
    -- 1.3.6.1.4.1.39553.10.3.10.221
    ex2DI7Normal OBJECT-TYPE
    SYNTAX INTEGER {
    no(0),
	nc(1)
    }
    MAX-ACCESS read-write
    STATUS current
    DESCRIPTION
    "EX2-DI7 input state when normal(no alarm)
    0:NO;
	1:NC
    "
    ::= { digitalInputAndOutputParameter 221 }
    -- 1.3.6.1.4.1.39553.10.3.10.222
    ex2DI8Normal OBJECT-TYPE
    SYNTAX INTEGER {
    no(0),
	nc(1)
    }
    MAX-ACCESS read-write
    STATUS current
    DESCRIPTION
    "EX2-DI8 input state when normal(no alarm)
    0:NO;
	1:NC
    "
    ::= { digitalInputAndOutputParameter 222 }
    -- 1.3.6.1.4.1.39553.10.3.10.223
    ex3DI1Normal OBJECT-TYPE
    SYNTAX INTEGER {
    no(0),
	nc(1)
    }
    MAX-ACCESS read-write
    STATUS current
    DESCRIPTION
    "EX3-DI1 input state when normal(no alarm)
    0:NO;
	1:NC
    "
    ::= { digitalInputAndOutputParameter 223 }
    -- 1.3.6.1.4.1.39553.10.3.10.224
    ex3DI2Normal OBJECT-TYPE
    SYNTAX INTEGER {
    no(0),
	nc(1)
    }
    MAX-ACCESS read-write
    STATUS current
    DESCRIPTION
    "EX3-DI2 input state when normal(no alarm)
    0:NO;
	1:NC
    "
    ::= { digitalInputAndOutputParameter 224 }
    -- 1.3.6.1.4.1.39553.10.3.10.225
    ex3DI3Normal OBJECT-TYPE
    SYNTAX INTEGER {
    no(0),
	nc(1)
    }
    MAX-ACCESS read-write
    STATUS current
    DESCRIPTION
    "EX3-DI3 input state when normal(no alarm)
    0:NO;
	1:NC
    "
    ::= { digitalInputAndOutputParameter 225 }
    -- 1.3.6.1.4.1.39553.10.3.10.226
    ex3DI4Normal OBJECT-TYPE
    SYNTAX INTEGER {
    no(0),
	nc(1)
    }
    MAX-ACCESS read-write
    STATUS current
    DESCRIPTION
    "EX3-DI4 input state when normal(no alarm)
    0:NO;
	1:NC
    "
    ::= { digitalInputAndOutputParameter 226 }
    -- 1.3.6.1.4.1.39553.10.3.10.227
    ex3DI5Normal OBJECT-TYPE
    SYNTAX INTEGER {
    no(0),
	nc(1)
    }
    MAX-ACCESS read-write
    STATUS current
    DESCRIPTION
    "EX3-DI5 input state when normal(no alarm)
    0:NO;
	1:NC
    "
    ::= { digitalInputAndOutputParameter 227 }
    -- 1.3.6.1.4.1.39553.10.3.10.228
    ex3DI6Normal OBJECT-TYPE
    SYNTAX INTEGER {
    no(0),
	nc(1)
    }
    MAX-ACCESS read-write
    STATUS current
    DESCRIPTION
    "EX3-DI6 input state when normal(no alarm)
    0:NO;
	1:NC
    "
    ::= { digitalInputAndOutputParameter 228 }
    -- 1.3.6.1.4.1.39553.10.3.10.229
    ex3DI7Normal OBJECT-TYPE
    SYNTAX INTEGER {
    no(0),
	nc(1)
    }
    MAX-ACCESS read-write
    STATUS current
    DESCRIPTION
    "EX3-DI7 input state when normal(no alarm)
    0:NO;
	1:NC
    "
    ::= { digitalInputAndOutputParameter 229 }
    -- 1.3.6.1.4.1.39553.10.3.10.230
    ex3DI8Normal OBJECT-TYPE
    SYNTAX INTEGER {
    no(0),
	nc(1)
    }
    MAX-ACCESS read-write
    STATUS current
    DESCRIPTION
    "EX3-DI8 input state when normal(no alarm)
    0:NO;
	1:NC
    "
    ::= { digitalInputAndOutputParameter 230 }
    -- 1.3.6.1.4.1.39553.10.3.10.231
    ex4DI1Normal OBJECT-TYPE
    SYNTAX INTEGER {
    no(0),
	nc(1)
    }
    MAX-ACCESS read-write
    STATUS current
    DESCRIPTION
    "EX4-DI1 input state when normal(no alarm)
    0:NO;
	1:NC
    "
    ::= { digitalInputAndOutputParameter 231 }
    -- 1.3.6.1.4.1.39553.10.3.10.232
    ex4DI2Normal OBJECT-TYPE
    SYNTAX INTEGER {
    no(0),
	nc(1)
    }
    MAX-ACCESS read-write
    STATUS current
    DESCRIPTION
    "EX4-DI2 input state when normal(no alarm)
    0:NO;
	1:NC
    "
    ::= { digitalInputAndOutputParameter 232 }
    -- 1.3.6.1.4.1.39553.10.3.10.233
    ex4DI3Normal OBJECT-TYPE
    SYNTAX INTEGER {
    no(0),
	nc(1)
    }
    MAX-ACCESS read-write
    STATUS current
    DESCRIPTION
    "EX4-DI3 input state when normal(no alarm)
    0:NO;
	1:NC
    "
    ::= { digitalInputAndOutputParameter 233 }
    -- 1.3.6.1.4.1.39553.10.3.10.234
    ex4DI4Normal OBJECT-TYPE
    SYNTAX INTEGER {
    no(0),
	nc(1)
    }
    MAX-ACCESS read-write
    STATUS current
    DESCRIPTION
    "EX4-DI4 input state when normal(no alarm)
    0:NO;
	1:NC
    "
    ::= { digitalInputAndOutputParameter 234 }
    -- 1.3.6.1.4.1.39553.10.3.10.235
    ex4DI5Normal OBJECT-TYPE
    SYNTAX INTEGER {
    no(0),
	nc(1)
    }
    MAX-ACCESS read-write
    STATUS current
    DESCRIPTION
    "EX4-DI5 input state when normal(no alarm)
    0:NO;
	1:NC
    "
    ::= { digitalInputAndOutputParameter 235 }
    -- 1.3.6.1.4.1.39553.10.3.10.236
    ex4DI6Normal OBJECT-TYPE
    SYNTAX INTEGER {
    no(0),
	nc(1)
    }
    MAX-ACCESS read-write
    STATUS current
    DESCRIPTION
    "EX4-DI6 input state when normal(no alarm)
    0:NO;
	1:NC
    "
    ::= { digitalInputAndOutputParameter 236 }
    -- 1.3.6.1.4.1.39553.10.3.10.237
    ex4DI7Normal OBJECT-TYPE
    SYNTAX INTEGER {
    no(0),
	nc(1)
    }
    MAX-ACCESS read-write
    STATUS current
    DESCRIPTION
    "EX4-DI7 input state when normal(no alarm)
    0:NO;
	1:NC
    "
    ::= { digitalInputAndOutputParameter 237 }
    -- 1.3.6.1.4.1.39553.10.3.10.238
    ex4DI8Normal OBJECT-TYPE
    SYNTAX INTEGER {
    no(0),
	nc(1)
    }
    MAX-ACCESS read-write
    STATUS current
    DESCRIPTION
    "EX4-DI8 input state when normal(no alarm)
    0:NO;
	1:NC
    "
    ::= { digitalInputAndOutputParameter 238 }
    -- 1.3.6.1.4.1.39553.10.3.10.239
    ex5DI1Normal OBJECT-TYPE
    SYNTAX INTEGER {
    no(0),
	nc(1)
    }
    MAX-ACCESS read-write
    STATUS current
    DESCRIPTION
    "EX5-DI1 input state when normal(no alarm)
    0:NO;
	1:NC
    "
    ::= { digitalInputAndOutputParameter 239 }
    -- 1.3.6.1.4.1.39553.10.3.10.240
    ex5DI2Normal OBJECT-TYPE
    SYNTAX INTEGER {
    no(0),
	nc(1)
    }
    MAX-ACCESS read-write
    STATUS current
    DESCRIPTION
    "EX5-DI2 input state when normal(no alarm)
    0:NO;
	1:NC
    "
    ::= { digitalInputAndOutputParameter 240 }
    -- 1.3.6.1.4.1.39553.10.3.10.241
    ex5DI3Normal OBJECT-TYPE
    SYNTAX INTEGER {
    no(0),
	nc(1)
    }
    MAX-ACCESS read-write
    STATUS current
    DESCRIPTION
    "EX5-DI3 input state when normal(no alarm)
    0:NO;
	1:NC
    "
    ::= { digitalInputAndOutputParameter 241 }
    -- 1.3.6.1.4.1.39553.10.3.10.242
    ex5DI4Normal OBJECT-TYPE
    SYNTAX INTEGER {
    no(0),
	nc(1)
    }
    MAX-ACCESS read-write
    STATUS current
    DESCRIPTION
    "EX5-DI4 input state when normal(no alarm)
    0:NO;
	1:NC
    "
    ::= { digitalInputAndOutputParameter 242 }
    -- 1.3.6.1.4.1.39553.10.3.10.243
    ex5DI5Normal OBJECT-TYPE
    SYNTAX INTEGER {
    no(0),
	nc(1)
    }
    MAX-ACCESS read-write
    STATUS current
    DESCRIPTION
    "EX5-DI5 input state when normal(no alarm)
    0:NO;
	1:NC
    "
    ::= { digitalInputAndOutputParameter 243 }
    -- 1.3.6.1.4.1.39553.10.3.10.244
    ex5DI6Normal OBJECT-TYPE
    SYNTAX INTEGER {
    no(0),
	nc(1)
    }
    MAX-ACCESS read-write
    STATUS current
    DESCRIPTION
    "EX5-DI6 input state when normal(no alarm)
    0:NO;
	1:NC
    "
    ::= { digitalInputAndOutputParameter 244 }
    -- 1.3.6.1.4.1.39553.10.3.10.245
    ex5DI7Normal OBJECT-TYPE
    SYNTAX INTEGER {
    no(0),
	nc(1)
    }
    MAX-ACCESS read-write
    STATUS current
    DESCRIPTION
    "EX5-DI7 input state when normal(no alarm)
    0:NO;
	1:NC
    "
    ::= { digitalInputAndOutputParameter 245 }
    -- 1.3.6.1.4.1.39553.10.3.10.246
    ex5DI8Normal OBJECT-TYPE
    SYNTAX INTEGER {
    no(0),
	nc(1)
    }
    MAX-ACCESS read-write
    STATUS current
    DESCRIPTION
    "EX5-DI8 input state when normal(no alarm)
    0:NO;
	1:NC
    "
    ::= { digitalInputAndOutputParameter 246 }
    -- 1.3.6.1.4.1.39553.10.3.10.301
    di1NameChoose OBJECT-TYPE
    SYNTAX INTEGER {
    userDefine(0),
    water(1),
    door(2),
    hez(3),
    air(4),
    fan(5)
    }
    MAX-ACCESS read-write
    STATUS current
    DESCRIPTION
    "DI1 name choose commonly 
    0:user define;
    1:water;
    2:door;
    3:HEX;
    4:air;
    5:fan;
    "
    ::= { digitalInputAndOutputParameter 301 }
    -- 1.3.6.1.4.1.39553.10.3.10.302
    di2NameChoose OBJECT-TYPE
    SYNTAX INTEGER {
    userDefine(0),
    water(1),
    door(2),
    hez(3),
    air(4),
    fan(5)
    }
    MAX-ACCESS read-write
    STATUS current
    DESCRIPTION
    "DI2 name choose commonly
    0:user define;
    1:water;
    2:door;
    3:HEX;
    4:air;
    5:fan;
    "
    ::= { digitalInputAndOutputParameter 302 }
    -- 1.3.6.1.4.1.39553.10.3.10.303
    di3NameChoose OBJECT-TYPE
    SYNTAX INTEGER {
    userDefine(0),
    water(1),
    door(2),
    hez(3),
    air(4),
    fan(5)
    }
    MAX-ACCESS read-write
    STATUS current
    DESCRIPTION
    "DI3 name choose commonly
    0:user define;
    1:water;
    2:door;
    3:HEX;
    4:air;
    5:fan;
    "
    ::= { digitalInputAndOutputParameter 303 }
    -- 1.3.6.1.4.1.39553.10.3.10.304
    di4NameChoose OBJECT-TYPE
    SYNTAX INTEGER {
    userDefine(0),
    water(1),
    door(2),
    hez(3),
    air(4),
    fan(5)
    }
    MAX-ACCESS read-write
    STATUS current
    DESCRIPTION
    "DI4 name choose commonly
    0:user define;
    1:water;
    2:door;
    3:HEX;
    4:air;
    5:fan;
    "
    ::= { digitalInputAndOutputParameter 304 }
    -- 1.3.6.1.4.1.39553.10.3.10.305
    di5NameChoose OBJECT-TYPE
    SYNTAX INTEGER {
    userDefine(0),
    water(1),
    door(2),
    hez(3),
    air(4),
    fan(5)
    }
    MAX-ACCESS read-write
    STATUS current
    DESCRIPTION
    "DI5 name choose commonly
    0:user define;
    1:water;
    2:door;
    3:HEX;
    4:air;
    5:fan;
    "
    ::= { digitalInputAndOutputParameter 305 }
    -- 1.3.6.1.4.1.39553.10.3.10.306
    di6NameChoose OBJECT-TYPE
    SYNTAX INTEGER {
    userDefine(0),
    water(1),
    door(2),
    hez(3),
    air(4),
    fan(5)
    }
    MAX-ACCESS read-write
    STATUS current
    DESCRIPTION
    "DI6 name choose commonly
    0:user define;
    1:water;
    2:door;
    3:HEX;
    4:air;
    5:fan;
    "
    ::= { digitalInputAndOutputParameter 306 }
    -- 1.3.6.1.4.1.39553.10.3.10.307
    ex1DI1NameChoose OBJECT-TYPE
    SYNTAX INTEGER {
    userDefine(0),
    water(1),
    door(2),
    hez(3),
    air(4),
    fan(5)
    }
    MAX-ACCESS read-write
    STATUS current
    DESCRIPTION
    "EX1-DI1 name choose commonly 
    0:user define;
    1:water;
    2:door;
    3:HEX;
    4:air;
    5:fan;
    "
    ::= { digitalInputAndOutputParameter 307 }
    -- 1.3.6.1.4.1.39553.10.3.10.308
    ex1DI2NameChoose OBJECT-TYPE
    SYNTAX INTEGER {
    userDefine(0),
    water(1),
    door(2),
    hez(3),
    air(4),
    fan(5)
    }
    MAX-ACCESS read-write
    STATUS current
    DESCRIPTION
    "EX1-DI2 name choose commonly
    0:user define;
    1:water;
    2:door;
    3:HEX;
    4:air;
    5:fan;
    "
    ::= { digitalInputAndOutputParameter 308 }
    -- 1.3.6.1.4.1.39553.10.3.10.309
    ex1DI3NameChoose OBJECT-TYPE
    SYNTAX INTEGER {
    userDefine(0),
    water(1),
    door(2),
    hez(3),
    air(4),
    fan(5)
    }
    MAX-ACCESS read-write
    STATUS current
    DESCRIPTION
    "EX1-DI3 name choose commonly
    0:user define;
    1:water;
    2:door;
    3:HEX;
    4:air;
    5:fan;
    "
    ::= { digitalInputAndOutputParameter 309 }
    -- 1.3.6.1.4.1.39553.10.3.10.310
    ex1DI4NameChoose OBJECT-TYPE
    SYNTAX INTEGER {
    userDefine(0),
    water(1),
    door(2),
    hez(3),
    air(4),
    fan(5)
    }
    MAX-ACCESS read-write
    STATUS current
    DESCRIPTION
    "EX1-DI4 name choose commonly
    0:user define;
    1:water;
    2:door;
    3:HEX;
    4:air;
    5:fan;
    "
    ::= { digitalInputAndOutputParameter 310 }
    -- 1.3.6.1.4.1.39553.10.3.10.311
    ex1DI5NameChoose OBJECT-TYPE
    SYNTAX INTEGER {
    userDefine(0),
    water(1),
    door(2),
    hez(3),
    air(4),
    fan(5)
    }
    MAX-ACCESS read-write
    STATUS current
    DESCRIPTION
    "EX1-DI5 name choose commonly
    0:user define;
    1:water;
    2:door;
    3:HEX;
    4:air;
    5:fan;
    "
    ::= { digitalInputAndOutputParameter 311 }
    -- 1.3.6.1.4.1.39553.10.3.10.312
    ex1DI6NameChoose OBJECT-TYPE
    SYNTAX INTEGER {
    userDefine(0),
    water(1),
    door(2),
    hez(3),
    air(4),
    fan(5)
    }
    MAX-ACCESS read-write
    STATUS current
    DESCRIPTION
    "EX1-DI6 name choose commonly
    0:user define;
    1:water;
    2:door;
    3:HEX;
    4:air;
    5:fan;
    "
    ::= { digitalInputAndOutputParameter 312 }
    -- 1.3.6.1.4.1.39553.10.3.10.313
    ex1DI7NameChoose OBJECT-TYPE
    SYNTAX INTEGER {
    userDefine(0),
    water(1),
    door(2),
    hez(3),
    air(4),
    fan(5)
    }
    MAX-ACCESS read-write
    STATUS current
    DESCRIPTION
    "EX1-DI7 name choose commonly
    0:user define;
    1:water;
    2:door;
    3:HEX;
    4:air;
    5:fan;
    "
    ::= { digitalInputAndOutputParameter 313 }
    -- 1.3.6.1.4.1.39553.10.3.10.314
    ex1DI8NameChoose OBJECT-TYPE
    SYNTAX INTEGER {
    userDefine(0),
    water(1),
    door(2),
    hez(3),
    air(4),
    fan(5)
    }
    MAX-ACCESS read-write
    STATUS current
    DESCRIPTION
    "EX1-DI8 name choose commonly
    0:user define;
    1:water;
    2:door;
    3:HEX;
    4:air;
    5:fan;
    "
    ::= { digitalInputAndOutputParameter 314 }
    -- 1.3.6.1.4.1.39553.10.3.10.315
    ex2DI1NameChoose OBJECT-TYPE
    SYNTAX INTEGER {
    userDefine(0),
    water(1),
    door(2),
    hez(3),
    air(4),
    fan(5)
    }
    MAX-ACCESS read-write
    STATUS current
    DESCRIPTION
    "EX2-DI1 name choose commonly 
    0:user define;
    1:water;
    2:door;
    3:HEX;
    4:air;
    5:fan;
    "
    ::= { digitalInputAndOutputParameter 315 }
    -- 1.3.6.1.4.1.39553.10.3.10.316
    ex2DI2NameChoose OBJECT-TYPE
    SYNTAX INTEGER {
    userDefine(0),
    water(1),
    door(2),
    hez(3),
    air(4),
    fan(5)
    }
    MAX-ACCESS read-write
    STATUS current
    DESCRIPTION
    "EX2-DI2 name choose commonly
    0:user define;
    1:water;
    2:door;
    3:HEX;
    4:air;
    5:fan;
    "
    ::= { digitalInputAndOutputParameter 316 }
    -- 1.3.6.1.4.1.39553.10.3.10.317
    ex2DI3NameChoose OBJECT-TYPE
    SYNTAX INTEGER {
    userDefine(0),
    water(1),
    door(2),
    hez(3),
    air(4),
    fan(5)
    }
    MAX-ACCESS read-write
    STATUS current
    DESCRIPTION
    "EX2-DI3 name choose commonly
    0:user define;
    1:water;
    2:door;
    3:HEX;
    4:air;
    5:fan;
    "
    ::= { digitalInputAndOutputParameter 317 }
    -- 1.3.6.1.4.1.39553.10.3.10.318
    ex2DI4NameChoose OBJECT-TYPE
    SYNTAX INTEGER {
    userDefine(0),
    water(1),
    door(2),
    hez(3),
    air(4),
    fan(5)
    }
    MAX-ACCESS read-write
    STATUS current
    DESCRIPTION
    "EX2-DI4 name choose commonly
    0:user define;
    1:water;
    2:door;
    3:HEX;
    4:air;
    5:fan;
    "
    ::= { digitalInputAndOutputParameter 318 }
    -- 1.3.6.1.4.1.39553.10.3.10.319
    ex2DI5NameChoose OBJECT-TYPE
    SYNTAX INTEGER {
    userDefine(0),
    water(1),
    door(2),
    hez(3),
    air(4),
    fan(5)
    }
    MAX-ACCESS read-write
    STATUS current
    DESCRIPTION
    "EX2-DI5 name choose commonly
    0:user define;
    1:water;
    2:door;
    3:HEX;
    4:air;
    5:fan;
    "
    ::= { digitalInputAndOutputParameter 319 }
    -- 1.3.6.1.4.1.39553.10.3.10.320
    ex2DI6NameChoose OBJECT-TYPE
    SYNTAX INTEGER {
    userDefine(0),
    water(1),
    door(2),
    hez(3),
    air(4),
    fan(5)
    }
    MAX-ACCESS read-write
    STATUS current
    DESCRIPTION
    "EX2-DI6 name choose commonly
    0:user define;
    1:water;
    2:door;
    3:HEX;
    4:air;
    5:fan;
    "
    ::= { digitalInputAndOutputParameter 320 }
    -- 1.3.6.1.4.1.39553.10.3.10.321
    ex2DI7NameChoose OBJECT-TYPE
    SYNTAX INTEGER {
    userDefine(0),
    water(1),
    door(2),
    hez(3),
    air(4),
    fan(5)
    }
    MAX-ACCESS read-write
    STATUS current
    DESCRIPTION
    "EX2-DI7 name choose commonly
    0:user define;
    1:water;
    2:door;
    3:HEX;
    4:air;
    5:fan;
    "
    ::= { digitalInputAndOutputParameter 321 }
    -- 1.3.6.1.4.1.39553.10.3.10.322
    ex2DI8NameChoose OBJECT-TYPE
    SYNTAX INTEGER {
    userDefine(0),
    water(1),
    door(2),
    hez(3),
    air(4),
    fan(5)
    }
    MAX-ACCESS read-write
    STATUS current
    DESCRIPTION
    "EX2-DI8 name choose commonly
    0:user define;
    1:water;
    2:door;
    3:HEX;
    4:air;
    5:fan;
    "
    ::= { digitalInputAndOutputParameter 322 }
    -- 1.3.6.1.4.1.39553.10.3.10.323
    ex3DI1NameChoose OBJECT-TYPE
    SYNTAX INTEGER {
    userDefine(0),
    water(1),
    door(2),
    hez(3),
    air(4),
    fan(5)
    }
    MAX-ACCESS read-write
    STATUS current
    DESCRIPTION
    "EX3-DI1 name choose commonly 
    0:user define;
    1:water;
    2:door;
    3:HEX;
    4:air;
    5:fan;
    "
    ::= { digitalInputAndOutputParameter 323 }
    -- 1.3.6.1.4.1.39553.10.3.10.324
    ex3DI2NameChoose OBJECT-TYPE
    SYNTAX INTEGER {
    userDefine(0),
    water(1),
    door(2),
    hez(3),
    air(4),
    fan(5)
    }
    MAX-ACCESS read-write
    STATUS current
    DESCRIPTION
    "EX3-DI2 name choose commonly
    0:user define;
    1:water;
    2:door;
    3:HEX;
    4:air;
    5:fan;
    "
    ::= { digitalInputAndOutputParameter 324 }
    -- 1.3.6.1.4.1.39553.10.3.10.325
    ex3DI3NameChoose OBJECT-TYPE
    SYNTAX INTEGER {
    userDefine(0),
    water(1),
    door(2),
    hez(3),
    air(4),
    fan(5)
    }
    MAX-ACCESS read-write
    STATUS current
    DESCRIPTION
    "EX3-DI3 name choose commonly
    0:user define;
    1:water;
    2:door;
    3:HEX;
    4:air;
    5:fan;
    "
    ::= { digitalInputAndOutputParameter 325 }
    -- 1.3.6.1.4.1.39553.10.3.10.326
    ex3DI4NameChoose OBJECT-TYPE
    SYNTAX INTEGER {
    userDefine(0),
    water(1),
    door(2),
    hez(3),
    air(4),
    fan(5)
    }
    MAX-ACCESS read-write
    STATUS current
    DESCRIPTION
    "EX3-DI4 name choose commonly
    0:user define;
    1:water;
    2:door;
    3:HEX;
    4:air;
    5:fan;
    "
    ::= { digitalInputAndOutputParameter 326 }
    -- 1.3.6.1.4.1.39553.10.3.10.327
    ex3DI5NameChoose OBJECT-TYPE
    SYNTAX INTEGER {
    userDefine(0),
    water(1),
    door(2),
    hez(3),
    air(4),
    fan(5)
    }
    MAX-ACCESS read-write
    STATUS current
    DESCRIPTION
    "EX3-DI5 name choose commonly
    0:user define;
    1:water;
    2:door;
    3:HEX;
    4:air;
    5:fan;
    "
    ::= { digitalInputAndOutputParameter 327 }
    -- 1.3.6.1.4.1.39553.10.3.10.328
    ex3DI6NameChoose OBJECT-TYPE
    SYNTAX INTEGER {
    userDefine(0),
    water(1),
    door(2),
    hez(3),
    air(4),
    fan(5)
    }
    MAX-ACCESS read-write
    STATUS current
    DESCRIPTION
    "EX3-DI6 name choose commonly
    0:user define;
    1:water;
    2:door;
    3:HEX;
    4:air;
    5:fan;
    "
    ::= { digitalInputAndOutputParameter 328 }
    -- 1.3.6.1.4.1.39553.10.3.10.329
    ex3DI7NameChoose OBJECT-TYPE
    SYNTAX INTEGER {
    userDefine(0),
    water(1),
    door(2),
    hez(3),
    air(4),
    fan(5)
    }
    MAX-ACCESS read-write
    STATUS current
    DESCRIPTION
    "EX3-DI7 name choose commonly
    0:user define;
    1:water;
    2:door;
    3:HEX;
    4:air;
    5:fan;
    "
    ::= { digitalInputAndOutputParameter 329 }
    -- 1.3.6.1.4.1.39553.10.3.10.330
    ex3DI8NameChoose OBJECT-TYPE
    SYNTAX INTEGER {
    userDefine(0),
    water(1),
    door(2),
    hez(3),
    air(4),
    fan(5)
    }
    MAX-ACCESS read-write
    STATUS current
    DESCRIPTION
    "EX3-DI8 name choose commonly
    0:user define;
    1:water;
    2:door;
    3:HEX;
    4:air;
    5:fan;
    "
    ::= { digitalInputAndOutputParameter 330 }
    -- 1.3.6.1.4.1.39553.10.3.10.331
    ex4DI1NameChoose OBJECT-TYPE
    SYNTAX INTEGER {
    userDefine(0),
    water(1),
    door(2),
    hez(3),
    air(4),
    fan(5)
    }
    MAX-ACCESS read-write
    STATUS current
    DESCRIPTION
    "EX4-DI1 name choose commonly 
    0:user define;
    1:water;
    2:door;
    3:HEX;
    4:air;
    5:fan;
    "
    ::= { digitalInputAndOutputParameter 331 }
    -- 1.3.6.1.4.1.39553.10.3.10.332
    ex4DI2NameChoose OBJECT-TYPE
    SYNTAX INTEGER {
    userDefine(0),
    water(1),
    door(2),
    hez(3),
    air(4),
    fan(5)
    }
    MAX-ACCESS read-write
    STATUS current
    DESCRIPTION
    "EX4-DI2 name choose commonly
    0:user define;
    1:water;
    2:door;
    3:HEX;
    4:air;
    5:fan;
    "
    ::= { digitalInputAndOutputParameter 332 }
    -- 1.3.6.1.4.1.39553.10.3.10.333
    ex4DI3NameChoose OBJECT-TYPE
    SYNTAX INTEGER {
    userDefine(0),
    water(1),
    door(2),
    hez(3),
    air(4),
    fan(5)
    }
    MAX-ACCESS read-write
    STATUS current
    DESCRIPTION
    "EX4-DI3 name choose commonly
    0:user define;
    1:water;
    2:door;
    3:HEX;
    4:air;
    5:fan;
    "
    ::= { digitalInputAndOutputParameter 333 }
    -- 1.3.6.1.4.1.39553.10.3.10.334
    ex4DI4NameChoose OBJECT-TYPE
    SYNTAX INTEGER {
    userDefine(0),
    water(1),
    door(2),
    hez(3),
    air(4),
    fan(5)
    }
    MAX-ACCESS read-write
    STATUS current
    DESCRIPTION
    "EX4-DI4 name choose commonly
    0:user define;
    1:water;
    2:door;
    3:HEX;
    4:air;
    5:fan;
    "
    ::= { digitalInputAndOutputParameter 334 }
    -- 1.3.6.1.4.1.39553.10.3.10.335
    ex4DI5NameChoose OBJECT-TYPE
    SYNTAX INTEGER {
    userDefine(0),
    water(1),
    door(2),
    hez(3),
    air(4),
    fan(5)
    }
    MAX-ACCESS read-write
    STATUS current
    DESCRIPTION
    "EX4-DI5 name choose commonly
    0:user define;
    1:water;
    2:door;
    3:HEX;
    4:air;
    5:fan;
    "
    ::= { digitalInputAndOutputParameter 335 }
    -- 1.3.6.1.4.1.39553.10.3.10.336
    ex4DI6NameChoose OBJECT-TYPE
    SYNTAX INTEGER {
    userDefine(0),
    water(1),
    door(2),
    hez(3),
    air(4),
    fan(5)
    }
    MAX-ACCESS read-write
    STATUS current
    DESCRIPTION
    "EX4-DI6 name choose commonly
    0:user define;
    1:water;
    2:door;
    3:HEX;
    4:air;
    5:fan;
    "
    ::= { digitalInputAndOutputParameter 336 }
    -- 1.3.6.1.4.1.39553.10.3.10.337
    ex4DI7NameChoose OBJECT-TYPE
    SYNTAX INTEGER {
    userDefine(0),
    water(1),
    door(2),
    hez(3),
    air(4),
    fan(5)
    }
    MAX-ACCESS read-write
    STATUS current
    DESCRIPTION
    "EX4-DI7 name choose commonly
    0:user define;
    1:water;
    2:door;
    3:HEX;
    4:air;
    5:fan;
    "
    ::= { digitalInputAndOutputParameter 337 }
    -- 1.3.6.1.4.1.39553.10.3.10.338
    ex4DI8NameChoose OBJECT-TYPE
    SYNTAX INTEGER {
    userDefine(0),
    water(1),
    door(2),
    hez(3),
    air(4),
    fan(5)
    }
    MAX-ACCESS read-write
    STATUS current
    DESCRIPTION
    "EX4-DI8 name choose commonly
    0:user define;
    1:water;
    2:door;
    3:HEX;
    4:air;
    5:fan;
    "
    ::= { digitalInputAndOutputParameter 338 }
    -- 1.3.6.1.4.1.39553.10.3.10.339
    ex5DI1NameChoose OBJECT-TYPE
    SYNTAX INTEGER {
    userDefine(0),
    water(1),
    door(2),
    hez(3),
    air(4),
    fan(5)
    }
    MAX-ACCESS read-write
    STATUS current
    DESCRIPTION
    "EX5-DI1 name choose commonly 
    0:user define;
    1:water;
    2:door;
    3:HEX;
    4:air;
    5:fan;
    "
    ::= { digitalInputAndOutputParameter 339 }
    -- 1.3.6.1.4.1.39553.10.3.10.340
    ex5DI2NameChoose OBJECT-TYPE
    SYNTAX INTEGER {
    userDefine(0),
    water(1),
    door(2),
    hez(3),
    air(4),
    fan(5)
    }
    MAX-ACCESS read-write
    STATUS current
    DESCRIPTION
    "EX5-DI2 name choose commonly
    0:user define;
    1:water;
    2:door;
    3:HEX;
    4:air;
    5:fan;
    "
    ::= { digitalInputAndOutputParameter 340 }
    -- 1.3.6.1.4.1.39553.10.3.10.341
    ex5DI3NameChoose OBJECT-TYPE
    SYNTAX INTEGER {
    userDefine(0),
    water(1),
    door(2),
    hez(3),
    air(4),
    fan(5)
    }
    MAX-ACCESS read-write
    STATUS current
    DESCRIPTION
    "EX5-DI3 name choose commonly
    0:user define;
    1:water;
    2:door;
    3:HEX;
    4:air;
    5:fan;
    "
    ::= { digitalInputAndOutputParameter 341 }
    -- 1.3.6.1.4.1.39553.10.3.10.342
    ex5DI4NameChoose OBJECT-TYPE
    SYNTAX INTEGER {
    userDefine(0),
    water(1),
    door(2),
    hez(3),
    air(4),
    fan(5)
    }
    MAX-ACCESS read-write
    STATUS current
    DESCRIPTION
    "EX5-DI4 name choose commonly
    0:user define;
    1:water;
    2:door;
    3:HEX;
    4:air;
    5:fan;
    "
    ::= { digitalInputAndOutputParameter 342 }
    -- 1.3.6.1.4.1.39553.10.3.10.343
    ex5DI5NameChoose OBJECT-TYPE
    SYNTAX INTEGER {
    userDefine(0),
    water(1),
    door(2),
    hez(3),
    air(4),
    fan(5)
    }
    MAX-ACCESS read-write
    STATUS current
    DESCRIPTION
    "EX5-DI5 name choose commonly
    0:user define;
    1:water;
    2:door;
    3:HEX;
    4:air;
    5:fan;
    "
    ::= { digitalInputAndOutputParameter 343 }
    -- 1.3.6.1.4.1.39553.10.3.10.344
    ex5DI6NameChoose OBJECT-TYPE
    SYNTAX INTEGER {
    userDefine(0),
    water(1),
    door(2),
    hez(3),
    air(4),
    fan(5)
    }
    MAX-ACCESS read-write
    STATUS current
    DESCRIPTION
    "EX5-DI6 name choose commonly
    0:user define;
    1:water;
    2:door;
    3:HEX;
    4:air;
    5:fan;
    "
    ::= { digitalInputAndOutputParameter 344 }
    -- 1.3.6.1.4.1.39553.10.3.10.345
    ex5DI7NameChoose OBJECT-TYPE
    SYNTAX INTEGER {
    userDefine(0),
    water(1),
    door(2),
    hez(3),
    air(4),
    fan(5)
    }
    MAX-ACCESS read-write
    STATUS current
    DESCRIPTION
    "EX5-DI7 name choose commonly
    0:user define;
    1:water;
    2:door;
    3:HEX;
    4:air;
    5:fan;
    "
    ::= { digitalInputAndOutputParameter 345 }
    -- 1.3.6.1.4.1.39553.10.3.10.346
    ex5DI8NameChoose OBJECT-TYPE
    SYNTAX INTEGER {
    userDefine(0),
    water(1),
    door(2),
    hez(3),
    air(4),
    fan(5)
    }
    MAX-ACCESS read-write
    STATUS current
    DESCRIPTION
    "EX5-DI8 name choose commonly
    0:user define;
    1:water;
    2:door;
    3:HEX;
    4:air;
    5:fan;
    "
    ::= { digitalInputAndOutputParameter 346 }
    -- 1.3.6.1.4.1.39553.10.3.10.401
    di1Name OBJECT-TYPE
    SYNTAX DisplayString (SIZE(0..19))
    MAX-ACCESS read-write
    STATUS current
    DESCRIPTION
    "DI1 name setting"
    ::= { digitalInputAndOutputParameter 401 }
    -- 1.3.6.1.4.1.39553.10.3.10.402
    di2Name OBJECT-TYPE
    SYNTAX DisplayString (SIZE(0..19))
    MAX-ACCESS read-write
    STATUS current
    DESCRIPTION
    "DI2 name setting"
    ::= { digitalInputAndOutputParameter 402 }
    -- 1.3.6.1.4.1.39553.10.3.10.403
    di3Name OBJECT-TYPE
    SYNTAX DisplayString (SIZE(0..19))
    MAX-ACCESS read-write
    STATUS current
    DESCRIPTION
    "DI3 name setting"
    ::= { digitalInputAndOutputParameter 403 }
    -- 1.3.6.1.4.1.39553.10.3.10.404
    di4Name OBJECT-TYPE
    SYNTAX DisplayString (SIZE(0..19))
    MAX-ACCESS read-write
    STATUS current
    DESCRIPTION
    "DI4 name setting"
    ::= { digitalInputAndOutputParameter 404 }
    -- 1.3.6.1.4.1.39553.10.3.10.405
    di5Name OBJECT-TYPE
    SYNTAX DisplayString (SIZE(0..19))
    MAX-ACCESS read-write
    STATUS current
    DESCRIPTION
    "DI5 name setting"
    ::= { digitalInputAndOutputParameter 405 }
    -- 1.3.6.1.4.1.39553.10.3.10.406
    di6Name OBJECT-TYPE
    SYNTAX DisplayString (SIZE(0..19))
    MAX-ACCESS read-write
    STATUS current
    DESCRIPTION
    "DI6 name setting"
    ::= { digitalInputAndOutputParameter 406 }
    -- 1.3.6.1.4.1.39553.10.3.10.407
    ex1DI1Name OBJECT-TYPE
    SYNTAX DisplayString (SIZE(0..19))
    MAX-ACCESS read-write
    STATUS current
    DESCRIPTION
    "EX1-DI1 name setting"
    ::= { digitalInputAndOutputParameter 407 }
    -- 1.3.6.1.4.1.39553.10.3.10.408
    ex1DI2Name OBJECT-TYPE
    SYNTAX DisplayString (SIZE(0..19))
    MAX-ACCESS read-write
    STATUS current
    DESCRIPTION
    "EX1-DI2 name setting"
    ::= { digitalInputAndOutputParameter 408 }
    -- 1.3.6.1.4.1.39553.10.3.10.409
    ex1DI3Name OBJECT-TYPE
    SYNTAX DisplayString (SIZE(0..19))
    MAX-ACCESS read-write
    STATUS current
    DESCRIPTION
    "EX1-DI3 name setting"
    ::= { digitalInputAndOutputParameter 409 }
    -- 1.3.6.1.4.1.39553.10.3.10.410
    ex1DI4Name OBJECT-TYPE
    SYNTAX DisplayString (SIZE(0..19))
    MAX-ACCESS read-write
    STATUS current
    DESCRIPTION
    "EX1-DI4 name setting"
    ::= { digitalInputAndOutputParameter 410 }
    -- 1.3.6.1.4.1.39553.10.3.10.411
    ex1DI5Name OBJECT-TYPE
    SYNTAX DisplayString (SIZE(0..19))
    MAX-ACCESS read-write
    STATUS current
    DESCRIPTION
    "EX1-DI5 name setting"
    ::= { digitalInputAndOutputParameter 411 }
    -- 1.3.6.1.4.1.39553.10.3.10.412
    ex1DI6Name OBJECT-TYPE
    SYNTAX DisplayString (SIZE(0..19))
    MAX-ACCESS read-write
    STATUS current
    DESCRIPTION
    "EX1-DI6 name setting"
    ::= { digitalInputAndOutputParameter 412 }
    -- 1.3.6.1.4.1.39553.10.3.10.413
    ex1DI7Name OBJECT-TYPE
    SYNTAX DisplayString (SIZE(0..19))
    MAX-ACCESS read-write
    STATUS current
    DESCRIPTION
    "EX1-DI7 name setting"
    ::= { digitalInputAndOutputParameter 413 }
    -- 1.3.6.1.4.1.39553.10.3.10.414
    ex1DI8Name OBJECT-TYPE
    SYNTAX DisplayString (SIZE(0..19))
    MAX-ACCESS read-write
    STATUS current
    DESCRIPTION
    "EX1-DI8 name setting"
    ::= { digitalInputAndOutputParameter 414 }
    -- 1.3.6.1.4.1.39553.10.3.10.415
    ex2DI1Name OBJECT-TYPE
    SYNTAX DisplayString (SIZE(0..19))
    MAX-ACCESS read-write
    STATUS current
    DESCRIPTION
    "EX2-DI1 name setting"
    ::= { digitalInputAndOutputParameter 415 }
    -- 1.3.6.1.4.1.39553.10.3.10.416
    ex2DI2Name OBJECT-TYPE
    SYNTAX DisplayString (SIZE(0..19))
    MAX-ACCESS read-write
    STATUS current
    DESCRIPTION
    "EX2-DI2 name setting"
    ::= { digitalInputAndOutputParameter 416 }
    -- 1.3.6.1.4.1.39553.10.3.10.417
    ex2DI3Name OBJECT-TYPE
    SYNTAX DisplayString (SIZE(0..19))
    MAX-ACCESS read-write
    STATUS current
    DESCRIPTION
    "EX2-DI3 name setting"
    ::= { digitalInputAndOutputParameter 417 }
    -- 1.3.6.1.4.1.39553.10.3.10.418
    ex2DI4Name OBJECT-TYPE
    SYNTAX DisplayString (SIZE(0..19))
    MAX-ACCESS read-write
    STATUS current
    DESCRIPTION
    "EX2-DI4 name setting"
    ::= { digitalInputAndOutputParameter 418 }
    -- 1.3.6.1.4.1.39553.10.3.10.419
    ex2DI5Name OBJECT-TYPE
    SYNTAX DisplayString (SIZE(0..19))
    MAX-ACCESS read-write
    STATUS current
    DESCRIPTION
    "EX2-DI5 name setting"
    ::= { digitalInputAndOutputParameter 419 }
    -- 1.3.6.1.4.1.39553.10.3.10.420
    ex2DI6Name OBJECT-TYPE
    SYNTAX DisplayString (SIZE(0..19))
    MAX-ACCESS read-write
    STATUS current
    DESCRIPTION
    "EX2-DI6 name setting"
    ::= { digitalInputAndOutputParameter 420 }
    -- 1.3.6.1.4.1.39553.10.3.10.421
    ex2DI7Name OBJECT-TYPE
    SYNTAX DisplayString (SIZE(0..19))
    MAX-ACCESS read-write
    STATUS current
    DESCRIPTION
    "EX2-DI7 name setting"
    ::= { digitalInputAndOutputParameter 421 }
    -- 1.3.6.1.4.1.39553.10.3.10.422
    ex2DI8Name OBJECT-TYPE
    SYNTAX DisplayString (SIZE(0..19))
    MAX-ACCESS read-write
    STATUS current
    DESCRIPTION
    "EX2-DI8 name setting"
    ::= { digitalInputAndOutputParameter 422 }
    -- 1.3.6.1.4.1.39553.10.3.10.423
    ex3DI1Name OBJECT-TYPE
    SYNTAX DisplayString (SIZE(0..19))
    MAX-ACCESS read-write
    STATUS current
    DESCRIPTION
    "EX3-DI1 name setting"
    ::= { digitalInputAndOutputParameter 423 }
    -- 1.3.6.1.4.1.39553.10.3.10.424
    ex3DI2Name OBJECT-TYPE
    SYNTAX DisplayString (SIZE(0..19))
    MAX-ACCESS read-write
    STATUS current
    DESCRIPTION
    "EX3-DI2 name setting"
    ::= { digitalInputAndOutputParameter 424 }
    -- 1.3.6.1.4.1.39553.10.3.10.425
    ex3DI3Name OBJECT-TYPE
    SYNTAX DisplayString (SIZE(0..19))
    MAX-ACCESS read-write
    STATUS current
    DESCRIPTION
    "EX3-DI3 name setting"
    ::= { digitalInputAndOutputParameter 425 }
    -- 1.3.6.1.4.1.39553.10.3.10.426
    ex3DI4Name OBJECT-TYPE
    SYNTAX DisplayString (SIZE(0..19))
    MAX-ACCESS read-write
    STATUS current
    DESCRIPTION
    "EX3-DI4 name setting"
    ::= { digitalInputAndOutputParameter 426 }
    -- 1.3.6.1.4.1.39553.10.3.10.427
    ex3DI5Name OBJECT-TYPE
    SYNTAX DisplayString (SIZE(0..19))
    MAX-ACCESS read-write
    STATUS current
    DESCRIPTION
    "EX3-DI5 name setting"
    ::= { digitalInputAndOutputParameter 427 }
    -- 1.3.6.1.4.1.39553.10.3.10.428
    ex3DI6Name OBJECT-TYPE
    SYNTAX DisplayString (SIZE(0..19))
    MAX-ACCESS read-write
    STATUS current
    DESCRIPTION
    "EX3-DI6 name setting"
    ::= { digitalInputAndOutputParameter 428 }
    -- 1.3.6.1.4.1.39553.10.3.10.429
    ex3DI7Name OBJECT-TYPE
    SYNTAX DisplayString (SIZE(0..19))
    MAX-ACCESS read-write
    STATUS current
    DESCRIPTION
    "EX3-DI7 name setting"
    ::= { digitalInputAndOutputParameter 429 }
    -- 1.3.6.1.4.1.39553.10.3.10.430
    ex3DI8Name OBJECT-TYPE
    SYNTAX DisplayString (SIZE(0..19))
    MAX-ACCESS read-write
    STATUS current
    DESCRIPTION
    "EX3-DI8 name setting"
    ::= { digitalInputAndOutputParameter 430 }
    -- 1.3.6.1.4.1.39553.10.3.10.431
    ex4DI1Name OBJECT-TYPE
    SYNTAX DisplayString (SIZE(0..19))
    MAX-ACCESS read-write
    STATUS current
    DESCRIPTION
    "EX4-DI1 name setting"
    ::= { digitalInputAndOutputParameter 431 }
    -- 1.3.6.1.4.1.39553.10.3.10.432
    ex4DI2Name OBJECT-TYPE
    SYNTAX DisplayString (SIZE(0..19))
    MAX-ACCESS read-write
    STATUS current
    DESCRIPTION
    "EX4-DI2 name setting"
    ::= { digitalInputAndOutputParameter 432 }
    -- 1.3.6.1.4.1.39553.10.3.10.433
    ex4DI3Name OBJECT-TYPE
    SYNTAX DisplayString (SIZE(0..19))
    MAX-ACCESS read-write
    STATUS current
    DESCRIPTION
    "EX4-DI3 name setting"
    ::= { digitalInputAndOutputParameter 433 }
    -- 1.3.6.1.4.1.39553.10.3.10.434
    ex4DI4Name OBJECT-TYPE
    SYNTAX DisplayString (SIZE(0..19))
    MAX-ACCESS read-write
    STATUS current
    DESCRIPTION
    "EX4-DI4 name setting"
    ::= { digitalInputAndOutputParameter 434 }
    -- 1.3.6.1.4.1.39553.10.3.10.435
    ex4DI5Name OBJECT-TYPE
    SYNTAX DisplayString (SIZE(0..19))
    MAX-ACCESS read-write
    STATUS current
    DESCRIPTION
    "EX4-DI5 name setting"
    ::= { digitalInputAndOutputParameter 435 }
    -- 1.3.6.1.4.1.39553.10.3.10.436
    ex4DI6Name OBJECT-TYPE
    SYNTAX DisplayString (SIZE(0..19))
    MAX-ACCESS read-write
    STATUS current
    DESCRIPTION
    "EX4-DI6 name setting"
    ::= { digitalInputAndOutputParameter 436 }
    -- 1.3.6.1.4.1.39553.10.3.10.437
    ex4DI7Name OBJECT-TYPE
    SYNTAX DisplayString (SIZE(0..19))
    MAX-ACCESS read-write
    STATUS current
    DESCRIPTION
    "EX4-DI7 name setting"
    ::= { digitalInputAndOutputParameter 437 }
    -- 1.3.6.1.4.1.39553.10.3.10.438
    ex4DI8Name OBJECT-TYPE
    SYNTAX DisplayString (SIZE(0..19))
    MAX-ACCESS read-write
    STATUS current
    DESCRIPTION
    "EX4-DI8 name setting"
    ::= { digitalInputAndOutputParameter 438 }
    -- 1.3.6.1.4.1.39553.10.3.10.439
    ex5DI1Name OBJECT-TYPE
    SYNTAX DisplayString (SIZE(0..19))
    MAX-ACCESS read-write
    STATUS current
    DESCRIPTION
    "EX5-DI1 name setting"
    ::= { digitalInputAndOutputParameter 439 }
    -- 1.3.6.1.4.1.39553.10.3.10.440
    ex5DI2Name OBJECT-TYPE
    SYNTAX DisplayString (SIZE(0..19))
    MAX-ACCESS read-write
    STATUS current
    DESCRIPTION
    "EX5-DI2 name setting"
    ::= { digitalInputAndOutputParameter 440 }
    -- 1.3.6.1.4.1.39553.10.3.10.441
    ex5DI3Name OBJECT-TYPE
    SYNTAX DisplayString (SIZE(0..19))
    MAX-ACCESS read-write
    STATUS current
    DESCRIPTION
    "EX5-DI3 name setting"
    ::= { digitalInputAndOutputParameter 441 }
    -- 1.3.6.1.4.1.39553.10.3.10.442
    ex5DI4Name OBJECT-TYPE
    SYNTAX DisplayString (SIZE(0..19))
    MAX-ACCESS read-write
    STATUS current
    DESCRIPTION
    "EX5-DI4 name setting"
    ::= { digitalInputAndOutputParameter 442 }
    -- 1.3.6.1.4.1.39553.10.3.10.443
    ex5DI5Name OBJECT-TYPE
    SYNTAX DisplayString (SIZE(0..19))
    MAX-ACCESS read-write
    STATUS current
    DESCRIPTION
    "EX5-DI5 name setting"
    ::= { digitalInputAndOutputParameter 443 }
    -- 1.3.6.1.4.1.39553.10.3.10.444
    ex5DI6Name OBJECT-TYPE
    SYNTAX DisplayString (SIZE(0..19))
    MAX-ACCESS read-write
    STATUS current
    DESCRIPTION
    "EX5-DI6 name setting"
    ::= { digitalInputAndOutputParameter 444 }
    -- 1.3.6.1.4.1.39553.10.3.10.445
    ex5DI7Name OBJECT-TYPE
    SYNTAX DisplayString (SIZE(0..19))
    MAX-ACCESS read-write
    STATUS current
    DESCRIPTION
    "EX5-DI7 name setting"
    ::= { digitalInputAndOutputParameter 445 }
    -- 1.3.6.1.4.1.39553.10.3.10.446
    ex5DI8Name OBJECT-TYPE
    SYNTAX DisplayString (SIZE(0..19))
    MAX-ACCESS read-write
    STATUS current
    DESCRIPTION
    "EX5-DI8 name setting"
    ::= { digitalInputAndOutputParameter 446 }

    
------------------------------------------------------------
--  Characteristic string for DC Distribution { dcDistribution 12 }
------------------------------------------------------------    
    -- 1.3.6.1.4.1.39553.10.3.12
    characteristic OBJECT IDENTIFIER ::= { dcDistribution 12 }

  -- 1.3.6.1.4.1.39553.10.3.12.1
    companyName OBJECT-TYPE
    SYNTAX DisplayString (SIZE(0..39))
    MAX-ACCESS read-write
    STATUS current
    DESCRIPTION 
        "The name of manufacturer."
    ::= { characteristic 1 }
  -- 1.3.6.1.4.1.39553.10.3.12.2
    companyUrl OBJECT-TYPE
    SYNTAX DisplayString (SIZE(0..39))
    MAX-ACCESS read-write
    STATUS current
    DESCRIPTION 
        "The website of manufacturer."
    ::= { characteristic 2 }    
  -- 1.3.6.1.4.1.39553.10.3.12.3
    productModel OBJECT-TYPE
    SYNTAX DisplayString (SIZE(0..31))
    MAX-ACCESS read-write
    STATUS current
    DESCRIPTION 
        "The product Model of controller."
    ::= { characteristic 3 }
  -- 1.3.6.1.4.1.39553.10.3.12.4
    contactPhone OBJECT-TYPE
    SYNTAX DisplayString (SIZE(0..19))
    MAX-ACCESS read-write
    STATUS current
    DESCRIPTION 
        "The contact phone number of manufacturer."
    ::= { characteristic 4 }
  -- 1.3.6.1.4.1.39553.10.3.12.5
    companyAddress OBJECT-TYPE
    SYNTAX DisplayString (SIZE(0..99))
    MAX-ACCESS read-write
    STATUS current
    DESCRIPTION 
        "The contact address of manufacturer."
    ::= { characteristic 5 }
  -- 1.3.6.1.4.1.39553.10.3.12.6
    productBarcode OBJECT-TYPE
    SYNTAX DisplayString (SIZE(0..20))
    MAX-ACCESS read-only
    STATUS current
    DESCRIPTION 
        "The barcode of controller."
    ::= { characteristic 6 }
  -- 1.3.6.1.4.1.39553.10.3.12.7
    softwareVersion OBJECT-TYPE
    SYNTAX DisplayString (SIZE(0..19))
    MAX-ACCESS read-only
    STATUS current
    DESCRIPTION 
        "The software version of controller."
    ::= { characteristic 7 }
    -- 1.3.6.1.4.1.39553.10.3.12.8
    installationYear OBJECT-TYPE
    SYNTAX INTEGER(0..2100)
    MAX-ACCESS read-write
    STATUS current
    DESCRIPTION 
        "Year of installation date.
         The actual value = The receive data.
         "  
    ::= { characteristic 8 }
    -- 1.3.6.1.4.1.39553.10.3.12.9
    installationMonth OBJECT-TYPE
    SYNTAX INTEGER(1..12)
    MAX-ACCESS read-write
    STATUS current
    DESCRIPTION 
        "Month of installation date.
         The actual value = The receive data.
         "  
    ::= { characteristic 9 }
    -- 1.3.6.1.4.1.39553.10.3.12.10
    installationDay OBJECT-TYPE
    SYNTAX INTEGER(1..31)
    MAX-ACCESS read-write
    STATUS current
    DESCRIPTION 
        "Day of installation date.
         The actual value = The receive data.
         "  
    ::= { characteristic 10 }
    -- 1.3.6.1.4.1.39553.10.3.12.11
    installationHour OBJECT-TYPE
    SYNTAX INTEGER(0..23)
    MAX-ACCESS read-write
    STATUS current
    DESCRIPTION 
        "Hour of installation date.
         The actual value = The receive data.
         "  
    ::= { characteristic 11 }
    -- 1.3.6.1.4.1.39553.10.3.12.12
    installationMinute OBJECT-TYPE
    SYNTAX INTEGER(0..59)
    MAX-ACCESS read-write
    STATUS current
    DESCRIPTION 
        "Minute of installation date.
         The actual value = The receive data.
         "  
    ::= { characteristic 12 }
    -- 1.3.6.1.4.1.39553.10.3.12.13
    installationSecond OBJECT-TYPE
    SYNTAX INTEGER(0..59)
    MAX-ACCESS read-write
    STATUS current
    DESCRIPTION 
        "Second of installation date.
         The actual value = The receive data.
         "  
    ::= { characteristic 13 }
    -- 1.3.6.1.4.1.39553.10.3.12.14
    totalRunTime OBJECT-TYPE
    SYNTAX INTEGER
    MAX-ACCESS read-only
    STATUS current
    DESCRIPTION 
        "Total run time of controller.
         The actual value = The receive data/100.
         The unit of actual value is hour.
         "  
    ::= { characteristic 14 }
    -- 1.3.6.1.4.1.39553.10.3.12.15
    --siteID OBJECT-TYPE
    --SYNTAX DisplayString (SIZE(0..30))
    --MAX-ACCESS read-write
    --STATUS current
    --DESCRIPTION 
        --"The ID of site."
    --::= { characteristic 15 }
    -- 1.3.6.1.4.1.39553.10.3.12.16
    --siteName OBJECT-TYPE
    --SYNTAX DisplayString (SIZE(0..30))
    --MAX-ACCESS read-write
    --STATUS current
    --DESCRIPTION 
        --"The name of site."
    --::= { characteristic 16 }
    -- 1.3.6.1.4.1.39553.10.3.12.17
    --siteAddress OBJECT-TYPE
    --SYNTAX DisplayString (SIZE(0..50))
    --MAX-ACCESS read-write
    --STATUS current
   -- DESCRIPTION 
       -- "The address of site."
    --::= { characteristic 17 }
    
------------------------------------------------------------
		ecoParameter OBJECT IDENTIFIER ::= { dcDistribution 16 }
  -- 1.3.6.1.4.1.39553.10.3.16.1
	ecoMode OBJECT-TYPE
	SYNTAX INTEGER {
		intelligentMode (0),
		timeMode (1),
		highEfficiencyMode (2)
	}
	MAX-ACCESS read-write
	STATUS current
	DESCRIPTION 
		"ECO running mode."
	::= { ecoParameter 1 }
  -- 1.3.6.1.4.1.39553.10.3.16.101
	acdcRectifierECOEnable OBJECT-TYPE
	SYNTAX INTEGER {
		disable (0),
		enable (1)
	}
	MAX-ACCESS read-write
	STATUS current
	DESCRIPTION 
		"ACDC rectifier ECO enable."
	::= { ecoParameter 101 }
  -- 1.3.6.1.4.1.39553.10.3.16.102
	acdcRectifierPhaseBalanceEnable OBJECT-TYPE
	SYNTAX INTEGER {
		disable (0),
		enable (1)
	}
	MAX-ACCESS read-write
	STATUS current
	DESCRIPTION 
		"AC input phase balance enable."
	::= { ecoParameter 102 }
  -- 1.3.6.1.4.1.39553.10.3.16.103
	acdcRectifierECODelay OBJECT-TYPE
	SYNTAX INTEGER (0..9900)
	MAX-ACCESS read-write
	STATUS current
	DESCRIPTION 
		"ACDC rectifier ECO delay.
		 The actual value = The set or receive data / 100.
		 The unit of actual value is hour."
	::= { ecoParameter 103 }
  -- 1.3.6.1.4.1.39553.10.3.16.104
	acdcRectifierMinimumQuantity OBJECT-TYPE
	SYNTAX INTEGER (1..255)
	MAX-ACCESS read-write
	STATUS current
	DESCRIPTION 
		"ACDC rectifier minimum quantity.
		 The actual value = The set or receive data.
		 "
	::= { ecoParameter 104 }
  -- 1.3.6.1.4.1.39553.10.3.16.105
	acdcRectifierPowerOnLoadRate OBJECT-TYPE
	SYNTAX INTEGER (10000..95000)
	MAX-ACCESS read-write
	STATUS current
	DESCRIPTION 
		"The load rate for control power on the ACDC rectifier for ECO function.
		 The actual value = The set or receive data / 1000.
		 The unit of actual value is %."
	::= { ecoParameter 105 }
  -- 1.3.6.1.4.1.39553.10.3.16.106
	acdcRectifierOnOffPeriodECO OBJECT-TYPE
	SYNTAX INTEGER (1..72000)
	MAX-ACCESS read-write
	STATUS current
	DESCRIPTION 
		"The period for control on or off the ACDC rectifier for ECO function.
		 The actual value = The set or receive data / 100.
		 The unit of actual value is hour."
	::= { ecoParameter 106 }
  -- 1.3.6.1.4.1.39553.10.3.16.107
	acdcRectifierPowerOffLoadRate OBJECT-TYPE
	SYNTAX INTEGER (0..85000)
	MAX-ACCESS read-write
	STATUS current
	DESCRIPTION 
		"The load rate for control power off the ACDC rectifier for ECO function.
		 The actual value = The set or receive data / 1000.
		 The unit of actual value is %."
	::= { ecoParameter 107 }
  -- 1.3.6.1.4.1.39553.10.3.16.108
	acdcRectifierManualStartTest OBJECT-TYPE
	SYNTAX INTEGER {
		stop (0),
		start (1)
	}
	MAX-ACCESS read-write
	STATUS current
	DESCRIPTION 
		"ACDC rectifier manual start test."
	::= { ecoParameter 108 }
  -- 1.3.6.1.4.1.39553.10.3.16.109
	acdcRectifierManualTestResult OBJECT-TYPE
	SYNTAX INTEGER {
		fail (0),
		ok (1),
		running (2),
		autoMode (3)
	}
	MAX-ACCESS read-only
	STATUS current
	DESCRIPTION 
		"ACDC rectifier manual test result."
	::= { ecoParameter 109 }
  -- 1.3.6.1.4.1.39553.10.3.16.201
	dcdcConverterECOEnable OBJECT-TYPE
	SYNTAX INTEGER {
		disable (0),
		enable (1)
	}
	MAX-ACCESS read-write
	STATUS current
	DESCRIPTION 
		"DCDC converter ECO enable."
	::= { ecoParameter 201 }
  -- 1.3.6.1.4.1.39553.10.3.16.202
	dcdcConverterECODelay OBJECT-TYPE
	SYNTAX INTEGER (0..9900)
	MAX-ACCESS read-write
	STATUS current
	DESCRIPTION 
		"DCDC converter ECO delay.
		 The actual value = The set or receive data / 100.
		 The unit of actual value is hour."
	::= { ecoParameter 202 }
  -- 1.3.6.1.4.1.39553.10.3.16.203
	dcdcConverterMinimumQuantity OBJECT-TYPE
	SYNTAX INTEGER (1..255)
	MAX-ACCESS read-write
	STATUS current
	DESCRIPTION 
		"DCDC converter minimum quantity.
		 The actual value = The set or receive data.
		 "
	::= { ecoParameter 203 }
  -- 1.3.6.1.4.1.39553.10.3.16.204
	dcdcConverterPowerOnLoadRate OBJECT-TYPE
	SYNTAX INTEGER (10000..95000)
	MAX-ACCESS read-write
	STATUS current
	DESCRIPTION 
		"The load rate for control power on the DCDC converter for ECO function.
		 The actual value = The set or receive data / 1000.
		 The unit of actual value is %."
	::= { ecoParameter 204 }
  -- 1.3.6.1.4.1.39553.10.3.16.205
	dcdcConverterOnOffPeriodECO OBJECT-TYPE
	SYNTAX INTEGER (1..72000)
	MAX-ACCESS read-write
	STATUS current
	DESCRIPTION 
		"The period for control on or off the DCDC converter for ECO function.
		 The actual value = The set or receive data / 100.
		 The unit of actual value is hour."
	::= { ecoParameter 205 }
  -- 1.3.6.1.4.1.39553.10.3.16.206
	dcdcConverterPowerOffLoadRate OBJECT-TYPE
	SYNTAX INTEGER (0..85000)
	MAX-ACCESS read-write
	STATUS current
	DESCRIPTION 
		"The load rate for control power off the DCDC converter for ECO function.
		 The actual value = The set or receive data / 1000.
		 The unit of actual value is %."
	::= { ecoParameter 206 }
  -- 1.3.6.1.4.1.39553.10.3.16.207
	dcdcConverterManualStartTest OBJECT-TYPE
	SYNTAX INTEGER {
		stop (0),
		start (1)
	}
	MAX-ACCESS read-write
	STATUS current
	DESCRIPTION 
		"DCDC converter manual start test."
	::= { ecoParameter 207 }
  -- 1.3.6.1.4.1.39553.10.3.16.208
	dcdcConverterManualTestResult OBJECT-TYPE
	SYNTAX INTEGER {
		fail (0),
		ok (1),
		running (2),
		autoMode (3)
	}
	MAX-ACCESS read-only
	STATUS current
	DESCRIPTION 
		"DCDC converter manual test result."
	::= { ecoParameter 208 }




    



------------------------------------------------------------
        pvLoopParameter OBJECT IDENTIFIER ::= { dcDistribution 18 }

pvLoopNoPowerFaultDelay OBJECT-TYPE
    SYNTAX INTEGER(10..6000)
    MAX-ACCESS read-write
    STATUS current
    DESCRIPTION "
        The delay of no power fault.
        The unit of actual value is second."
    ::= { pvLoopParameter 1 }
    
pvLoopNoPowerRecoveryDelay OBJECT-TYPE
    SYNTAX INTEGER(5..6000)
    MAX-ACCESS read-write
    STATUS current
    DESCRIPTION "
        The recovery delay of no power fault.
        The unit of actual value is second."
    ::= { pvLoopParameter 2 }
    
pvLoopPowerAttenuationAlarmDelay OBJECT-TYPE
    SYNTAX INTEGER(6..360000)
    MAX-ACCESS read-write
    STATUS current
    DESCRIPTION "
        The delay of power attenuation.
        The unit of actual value is second."
    ::= { pvLoopParameter 3 }

pvLoopPowerAttenuationRecoveryDelay OBJECT-TYPE
    SYNTAX INTEGER(6..360000)
    MAX-ACCESS read-write
    STATUS current
    DESCRIPTION "
        The recovery delay of power attenuation.
        The unit of actual value is second."
    ::= { pvLoopParameter 4 }

pvLoopPowerAttenuationAlarmValue OBJECT-TYPE
    SYNTAX INTEGER(100..9500)
    MAX-ACCESS read-write
    STATUS current
    DESCRIPTION "
        The alarm value of power attenuation alarm.
        The actual value = The receive data/100.
        The unit of actual value is percend."
    ::= { pvLoopParameter 5 }
    
pvLoopPowerAttenuationRecoveryValue OBJECT-TYPE
    SYNTAX INTEGER(100..9500)
    MAX-ACCESS read-write
    STATUS current
    DESCRIPTION "
        The recovery value of power attenuation alarm.
        The actual value = The receive data/100.
        The unit of actual value is percend."
    ::= { pvLoopParameter 6 }

noPowerDetectEnableOfSolarController1 OBJECT-TYPE
    SYNTAX INTEGER{
        disable (0),
        enable (1)
    }
    MAX-ACCESS read-write
    STATUS current
    DESCRIPTION 
        "Enable no power detection Of solar controller 1.
         Default:disable"       
    ::= { pvLoopParameter 7 }
noPowerDetectEnableOfSolarController2 OBJECT-TYPE
    SYNTAX INTEGER{
        disable (0),
        enable (1)
    }
    MAX-ACCESS read-write
    STATUS current
    DESCRIPTION 
        "Enable no power detection Of solar controller 2.
         Default:disable"       
    ::= { pvLoopParameter 8 }
noPowerDetectEnableOfSolarController3 OBJECT-TYPE
    SYNTAX INTEGER{
        disable (0),
        enable (1)
    }
    MAX-ACCESS read-write
    STATUS current
    DESCRIPTION 
        "Enable no power detection Of solar controller 3.
         Default:disable"       
    ::= { pvLoopParameter 9 }
noPowerDetectEnableOfSolarController4 OBJECT-TYPE
    SYNTAX INTEGER{
        disable (0),
        enable (1)
    }
    MAX-ACCESS read-write
    STATUS current
    DESCRIPTION 
        "Enable no power detection Of solar controller 4.
         Default:disable"       
    ::= { pvLoopParameter 10 }
noPowerDetectEnableOfSolarController5 OBJECT-TYPE
    SYNTAX INTEGER{
        disable (0),
        enable (1)
    }
    MAX-ACCESS read-write
    STATUS current
    DESCRIPTION 
        "Enable no power detection Of solar controller 5.
         Default:disable"       
    ::= { pvLoopParameter 11 }
noPowerDetectEnableOfSolarController6 OBJECT-TYPE
    SYNTAX INTEGER{
        disable (0),
        enable (1)
    }
    MAX-ACCESS read-write
    STATUS current
    DESCRIPTION 
        "Enable no power detection Of solar controller 6.
         Default:disable"       
    ::= { pvLoopParameter 12 }
noPowerDetectEnableOfSolarController7 OBJECT-TYPE
    SYNTAX INTEGER{
        disable (0),
        enable (1)
    }
    MAX-ACCESS read-write
    STATUS current
    DESCRIPTION 
        "Enable no power detection Of solar controller 7.
         Default:disable"       
    ::= { pvLoopParameter 13 }
noPowerDetectEnableOfSolarController8 OBJECT-TYPE
    SYNTAX INTEGER{
        disable (0),
        enable (1)
    }
    MAX-ACCESS read-write
    STATUS current
    DESCRIPTION 
        "Enable no power detection Of solar controller 8.
         Default:disable"       
    ::= { pvLoopParameter 14 }
noPowerDetectEnableOfSolarController9 OBJECT-TYPE
    SYNTAX INTEGER{
        disable (0),
        enable (1)
    }
    MAX-ACCESS read-write
    STATUS current
    DESCRIPTION 
        "Enable no power detection Of solar controller 9.
         Default:disable"       
    ::= { pvLoopParameter 15 }
noPowerDetectEnableOfSolarController10 OBJECT-TYPE
    SYNTAX INTEGER{
        disable (0),
        enable (1)
    }
    MAX-ACCESS read-write
    STATUS current
    DESCRIPTION 
        "Enable no power detection Of solar controller 10.
         Default:disable"       
    ::= { pvLoopParameter 16 }
noPowerDetectEnableOfSolarController11 OBJECT-TYPE
    SYNTAX INTEGER{
        disable (0),
        enable (1)
    }
    MAX-ACCESS read-write
    STATUS current
    DESCRIPTION 
        "Enable no power detection Of solar controller 11.
         Default:disable"       
    ::= { pvLoopParameter 17 }
noPowerDetectEnableOfSolarController12 OBJECT-TYPE
    SYNTAX INTEGER{
        disable (0),
        enable (1)
    }
    MAX-ACCESS read-write
    STATUS current
    DESCRIPTION 
        "Enable no power detection Of solar controller 12.
         Default:disable"       
    ::= { pvLoopParameter 18 }
noPowerDetectEnableOfSolarController13 OBJECT-TYPE
    SYNTAX INTEGER{
        disable (0),
        enable (1)
    }
    MAX-ACCESS read-write
    STATUS current
    DESCRIPTION 
        "Enable no power detection Of solar controller 13.
         Default:disable"       
    ::= { pvLoopParameter 19 }
noPowerDetectEnableOfSolarController14 OBJECT-TYPE
    SYNTAX INTEGER{
        disable (0),
        enable (1)
    }
    MAX-ACCESS read-write
    STATUS current
    DESCRIPTION 
        "Enable no power detection Of solar controller 14.
         Default:disable"       
    ::= { pvLoopParameter 20 }
noPowerDetectEnableOfSolarController15 OBJECT-TYPE
    SYNTAX INTEGER{
        disable (0),
        enable (1)
    }
    MAX-ACCESS read-write
    STATUS current
    DESCRIPTION 
        "Enable no power detection Of solar controller 15.
         Default:disable"       
    ::= { pvLoopParameter 21 }
noPowerDetectEnableOfSolarController16 OBJECT-TYPE
    SYNTAX INTEGER{
        disable (0),
        enable (1)
    }
    MAX-ACCESS read-write
    STATUS current
    DESCRIPTION 
        "Enable no power detection Of solar controller 16.
         Default:disable"       
    ::= { pvLoopParameter 22 }
noPowerDetectEnableOfSolarController17 OBJECT-TYPE
    SYNTAX INTEGER{
        disable (0),
        enable (1)
    }
    MAX-ACCESS read-write
    STATUS current
    DESCRIPTION 
        "Enable no power detection Of solar controller 17.
         Default:disable"       
    ::= { pvLoopParameter 23 }
noPowerDetectEnableOfSolarController18 OBJECT-TYPE
    SYNTAX INTEGER{
        disable (0),
        enable (1)
    }
    MAX-ACCESS read-write
    STATUS current
    DESCRIPTION 
        "Enable no power detection Of solar controller 18.
         Default:disable"       
    ::= { pvLoopParameter 24 }
noPowerDetectEnableOfSolarController19 OBJECT-TYPE
    SYNTAX INTEGER{
        disable (0),
        enable (1)
    }
    MAX-ACCESS read-write
    STATUS current
    DESCRIPTION 
        "Enable no power detection Of solar controller 19.
         Default:disable"       
    ::= { pvLoopParameter 25 }
noPowerDetectEnableOfSolarController20 OBJECT-TYPE
    SYNTAX INTEGER{
        disable (0),
        enable (1)
    }
    MAX-ACCESS read-write
    STATUS current
    DESCRIPTION 
        "Enable no power detection Of solar controller 20.
         Default:disable"       
    ::= { pvLoopParameter 26 }
noPowerDetectEnableOfSolarController21 OBJECT-TYPE
    SYNTAX INTEGER{
        disable (0),
        enable (1)
    }
    MAX-ACCESS read-write
    STATUS current
    DESCRIPTION 
        "Enable no power detection Of solar controller 21.
         Default:disable"       
    ::= { pvLoopParameter 27 }
noPowerDetectEnableOfSolarController22 OBJECT-TYPE
    SYNTAX INTEGER{
        disable (0),
        enable (1)
    }
    MAX-ACCESS read-write
    STATUS current
    DESCRIPTION 
        "Enable no power detection Of solar controller 22.
         Default:disable"       
    ::= { pvLoopParameter 28 }
noPowerDetectEnableOfSolarController23 OBJECT-TYPE
    SYNTAX INTEGER{
        disable (0),
        enable (1)
    }
    MAX-ACCESS read-write
    STATUS current
    DESCRIPTION 
        "Enable no power detection Of solar controller 23.
         Default:disable"       
    ::= { pvLoopParameter 29 }
noPowerDetectEnableOfSolarController24 OBJECT-TYPE
    SYNTAX INTEGER{
        disable (0),
        enable (1)
    }
    MAX-ACCESS read-write
    STATUS current
    DESCRIPTION 
        "Enable no power detection Of solar controller 24.
         Default:disable"       
    ::= { pvLoopParameter 30 }
noPowerDetectEnableOfSolarController25 OBJECT-TYPE
    SYNTAX INTEGER{
        disable (0),
        enable (1)
    }
    MAX-ACCESS read-write
    STATUS current
    DESCRIPTION 
        "Enable no power detection Of solar controller 25.
         Default:disable"       
    ::= { pvLoopParameter 31 }
noPowerDetectEnableOfSolarController26 OBJECT-TYPE
    SYNTAX INTEGER{
        disable (0),
        enable (1)
    }
    MAX-ACCESS read-write
    STATUS current
    DESCRIPTION 
        "Enable no power detection Of solar controller 26.
         Default:disable"       
    ::= { pvLoopParameter 32 }
noPowerDetectEnableOfSolarController27 OBJECT-TYPE
    SYNTAX INTEGER{
        disable (0),
        enable (1)
    }
    MAX-ACCESS read-write
    STATUS current
    DESCRIPTION 
        "Enable no power detection Of solar controller 27.
         Default:disable"       
    ::= { pvLoopParameter 33 }
noPowerDetectEnableOfSolarController28 OBJECT-TYPE
    SYNTAX INTEGER{
        disable (0),
        enable (1)
    }
    MAX-ACCESS read-write
    STATUS current
    DESCRIPTION 
        "Enable no power detection Of solar controller 28.
         Default:disable"       
    ::= { pvLoopParameter 34 }
noPowerDetectEnableOfSolarController29 OBJECT-TYPE
    SYNTAX INTEGER{
        disable (0),
        enable (1)
    }
    MAX-ACCESS read-write
    STATUS current
    DESCRIPTION 
        "Enable no power detection Of solar controller 29.
         Default:disable"       
    ::= { pvLoopParameter 35 }
noPowerDetectEnableOfSolarController30 OBJECT-TYPE
    SYNTAX INTEGER{
        disable (0),
        enable (1)
    }
    MAX-ACCESS read-write
    STATUS current
    DESCRIPTION 
        "Enable no power detection Of solar controller 30.
         Default:disable"       
    ::= { pvLoopParameter 36 }
noPowerDetectEnableOfSolarController31 OBJECT-TYPE
    SYNTAX INTEGER{
        disable (0),
        enable (1)
    }
    MAX-ACCESS read-write
    STATUS current
    DESCRIPTION 
        "Enable no power detection Of solar controller 31.
         Default:disable"       
    ::= { pvLoopParameter 37 }
noPowerDetectEnableOfSolarController32 OBJECT-TYPE
    SYNTAX INTEGER{
        disable (0),
        enable (1)
    }
    MAX-ACCESS read-write
    STATUS current
    DESCRIPTION 
        "Enable no power detection Of solar controller 32.
         Default:disable"       
    ::= { pvLoopParameter 38 }
powerAttenuationDetectEnableOfSolarController1 OBJECT-TYPE
    SYNTAX INTEGER{
        disable (0),
        enable (1)
    }
    MAX-ACCESS read-write
    STATUS current
    DESCRIPTION 
        "Enable power attenuation detection Of solar controller 1.
         Default:disable"       
    ::= { pvLoopParameter 39 }
powerAttenuationDetectEnableOfSolarController2 OBJECT-TYPE
    SYNTAX INTEGER{
        disable (0),
        enable (1)
    }
    MAX-ACCESS read-write
    STATUS current
    DESCRIPTION 
        "Enable power attenuation detection Of solar controller 2.
         Default:disable"       
    ::= { pvLoopParameter 40 }
powerAttenuationDetectEnableOfSolarController3 OBJECT-TYPE
    SYNTAX INTEGER{
        disable (0),
        enable (1)
    }
    MAX-ACCESS read-write
    STATUS current
    DESCRIPTION 
        "Enable power attenuation detection Of solar controller 3.
         Default:disable"       
    ::= { pvLoopParameter 41 }
powerAttenuationDetectEnableOfSolarController4 OBJECT-TYPE
    SYNTAX INTEGER{
        disable (0),
        enable (1)
    }
    MAX-ACCESS read-write
    STATUS current
    DESCRIPTION 
        "Enable power attenuation detection Of solar controller 4.
         Default:disable"       
    ::= { pvLoopParameter 42 }
powerAttenuationDetectEnableOfSolarController5 OBJECT-TYPE
    SYNTAX INTEGER{
        disable (0),
        enable (1)
    }
    MAX-ACCESS read-write
    STATUS current
    DESCRIPTION 
        "Enable power attenuation detection Of solar controller 5.
         Default:disable"       
    ::= { pvLoopParameter 43 }
powerAttenuationDetectEnableOfSolarController6 OBJECT-TYPE
    SYNTAX INTEGER{
        disable (0),
        enable (1)
    }
    MAX-ACCESS read-write
    STATUS current
    DESCRIPTION 
        "Enable power attenuation detection Of solar controller 6.
         Default:disable"       
    ::= { pvLoopParameter 44 }
powerAttenuationDetectEnableOfSolarController7 OBJECT-TYPE
    SYNTAX INTEGER{
        disable (0),
        enable (1)
    }
    MAX-ACCESS read-write
    STATUS current
    DESCRIPTION 
        "Enable power attenuation detection Of solar controller 7.
         Default:disable"       
    ::= { pvLoopParameter 45 }
powerAttenuationDetectEnableOfSolarController8 OBJECT-TYPE
    SYNTAX INTEGER{
        disable (0),
        enable (1)
    }
    MAX-ACCESS read-write
    STATUS current
    DESCRIPTION 
        "Enable power attenuation detection Of solar controller 8.
         Default:disable"       
    ::= { pvLoopParameter 46 }
powerAttenuationDetectEnableOfSolarController9 OBJECT-TYPE
    SYNTAX INTEGER{
        disable (0),
        enable (1)
    }
    MAX-ACCESS read-write
    STATUS current
    DESCRIPTION 
        "Enable power attenuation detection Of solar controller 9.
         Default:disable"       
    ::= { pvLoopParameter 47 }
powerAttenuationDetectEnableOfSolarController10 OBJECT-TYPE
    SYNTAX INTEGER{
        disable (0),
        enable (1)
    }
    MAX-ACCESS read-write
    STATUS current
    DESCRIPTION 
        "Enable power attenuation detection Of solar controller 10.
         Default:disable"       
    ::= { pvLoopParameter 48 }
powerAttenuationDetectEnableOfSolarController11 OBJECT-TYPE
    SYNTAX INTEGER{
        disable (0),
        enable (1)
    }
    MAX-ACCESS read-write
    STATUS current
    DESCRIPTION 
        "Enable power attenuation detection Of solar controller 11.
         Default:disable"       
    ::= { pvLoopParameter 49 }
powerAttenuationDetectEnableOfSolarController12 OBJECT-TYPE
    SYNTAX INTEGER{
        disable (0),
        enable (1)
    }
    MAX-ACCESS read-write
    STATUS current
    DESCRIPTION 
        "Enable power attenuation detection Of solar controller 12.
         Default:disable"       
    ::= { pvLoopParameter 50 }
powerAttenuationDetectEnableOfSolarController13 OBJECT-TYPE
    SYNTAX INTEGER{
        disable (0),
        enable (1)
    }
    MAX-ACCESS read-write
    STATUS current
    DESCRIPTION 
        "Enable power attenuation detection Of solar controller 13.
         Default:disable"       
    ::= { pvLoopParameter 51 }
powerAttenuationDetectEnableOfSolarController14 OBJECT-TYPE
    SYNTAX INTEGER{
        disable (0),
        enable (1)
    }
    MAX-ACCESS read-write
    STATUS current
    DESCRIPTION 
        "Enable power attenuation detection Of solar controller 14.
         Default:disable"       
    ::= { pvLoopParameter 52 }
powerAttenuationDetectEnableOfSolarController15 OBJECT-TYPE
    SYNTAX INTEGER{
        disable (0),
        enable (1)
    }
    MAX-ACCESS read-write
    STATUS current
    DESCRIPTION 
        "Enable power attenuation detection Of solar controller 15.
         Default:disable"       
    ::= { pvLoopParameter 53 }
powerAttenuationDetectEnableOfSolarController16 OBJECT-TYPE
    SYNTAX INTEGER{
        disable (0),
        enable (1)
    }
    MAX-ACCESS read-write
    STATUS current
    DESCRIPTION 
        "Enable power attenuation detection Of solar controller 16.
         Default:disable"       
    ::= { pvLoopParameter 54 }
powerAttenuationDetectEnableOfSolarController17 OBJECT-TYPE
    SYNTAX INTEGER{
        disable (0),
        enable (1)
    }
    MAX-ACCESS read-write
    STATUS current
    DESCRIPTION 
        "Enable power attenuation detection Of solar controller 17.
         Default:disable"       
    ::= { pvLoopParameter 55 }
powerAttenuationDetectEnableOfSolarController18 OBJECT-TYPE
    SYNTAX INTEGER{
        disable (0),
        enable (1)
    }
    MAX-ACCESS read-write
    STATUS current
    DESCRIPTION 
        "Enable power attenuation detection Of solar controller 18.
         Default:disable"       
    ::= { pvLoopParameter 56 }
powerAttenuationDetectEnableOfSolarController19 OBJECT-TYPE
    SYNTAX INTEGER{
        disable (0),
        enable (1)
    }
    MAX-ACCESS read-write
    STATUS current
    DESCRIPTION 
        "Enable power attenuation detection Of solar controller 19.
         Default:disable"       
    ::= { pvLoopParameter 57 }
powerAttenuationDetectEnableOfSolarController20 OBJECT-TYPE
    SYNTAX INTEGER{
        disable (0),
        enable (1)
    }
    MAX-ACCESS read-write
    STATUS current
    DESCRIPTION 
        "Enable power attenuation detection Of solar controller 20.
         Default:disable"       
    ::= { pvLoopParameter 58 }
powerAttenuationDetectEnableOfSolarController21 OBJECT-TYPE
    SYNTAX INTEGER{
        disable (0),
        enable (1)
    }
    MAX-ACCESS read-write
    STATUS current
    DESCRIPTION 
        "Enable power attenuation detection Of solar controller 21.
         Default:disable"       
    ::= { pvLoopParameter 59 }
powerAttenuationDetectEnableOfSolarController22 OBJECT-TYPE
    SYNTAX INTEGER{
        disable (0),
        enable (1)
    }
    MAX-ACCESS read-write
    STATUS current
    DESCRIPTION 
        "Enable power attenuation detection Of solar controller 22.
         Default:disable"       
    ::= { pvLoopParameter 60 }
powerAttenuationDetectEnableOfSolarController23 OBJECT-TYPE
    SYNTAX INTEGER{
        disable (0),
        enable (1)
    }
    MAX-ACCESS read-write
    STATUS current
    DESCRIPTION 
        "Enable power attenuation detection Of solar controller 23.
         Default:disable"       
    ::= { pvLoopParameter 61 }
powerAttenuationDetectEnableOfSolarController24 OBJECT-TYPE
    SYNTAX INTEGER{
        disable (0),
        enable (1)
    }
    MAX-ACCESS read-write
    STATUS current
    DESCRIPTION 
        "Enable power attenuation detection Of solar controller 24.
         Default:disable"       
    ::= { pvLoopParameter 62 }
powerAttenuationDetectEnableOfSolarController25 OBJECT-TYPE
    SYNTAX INTEGER{
        disable (0),
        enable (1)
    }
    MAX-ACCESS read-write
    STATUS current
    DESCRIPTION 
        "Enable power attenuation detection Of solar controller 25.
         Default:disable"       
    ::= { pvLoopParameter 63 }
powerAttenuationDetectEnableOfSolarController26 OBJECT-TYPE
    SYNTAX INTEGER{
        disable (0),
        enable (1)
    }
    MAX-ACCESS read-write
    STATUS current
    DESCRIPTION 
        "Enable power attenuation detection Of solar controller 26.
         Default:disable"       
    ::= { pvLoopParameter 64 }
powerAttenuationDetectEnableOfSolarController27 OBJECT-TYPE
    SYNTAX INTEGER{
        disable (0),
        enable (1)
    }
    MAX-ACCESS read-write
    STATUS current
    DESCRIPTION 
        "Enable power attenuation detection Of solar controller 27.
         Default:disable"       
    ::= { pvLoopParameter 65 }
powerAttenuationDetectEnableOfSolarController28 OBJECT-TYPE
    SYNTAX INTEGER{
        disable (0),
        enable (1)
    }
    MAX-ACCESS read-write
    STATUS current
    DESCRIPTION 
        "Enable power attenuation detection Of solar controller 28.
         Default:disable"       
    ::= { pvLoopParameter 66 }
powerAttenuationDetectEnableOfSolarController29 OBJECT-TYPE
    SYNTAX INTEGER{
        disable (0),
        enable (1)
    }
    MAX-ACCESS read-write
    STATUS current
    DESCRIPTION 
        "Enable power attenuation detection Of solar controller 29.
         Default:disable"       
    ::= { pvLoopParameter 67 }
powerAttenuationDetectEnableOfSolarController30 OBJECT-TYPE
    SYNTAX INTEGER{
        disable (0),
        enable (1)
    }
    MAX-ACCESS read-write
    STATUS current
    DESCRIPTION 
        "Enable power attenuation detection Of solar controller 30.
         Default:disable"       
    ::= { pvLoopParameter 68 }
powerAttenuationDetectEnableOfSolarController31 OBJECT-TYPE
    SYNTAX INTEGER{
        disable (0),
        enable (1)
    }
    MAX-ACCESS read-write
    STATUS current
    DESCRIPTION 
        "Enable power attenuation detection Of solar controller 31.
         Default:disable"       
    ::= { pvLoopParameter 69 }
powerAttenuationDetectEnableOfSolarController32 OBJECT-TYPE
    SYNTAX INTEGER{
        disable (0),
        enable (1)
    }
    MAX-ACCESS read-write
    STATUS current
    DESCRIPTION 
        "Enable power attenuation detection Of solar controller 32.
         Default:disable"       
    ::= { pvLoopParameter 70 }
peakPowerOfPVPanel1 OBJECT-TYPE
    SYNTAX INTEGER(1..65535)
    MAX-ACCESS read-write
    STATUS current
    DESCRIPTION "
        The peak power of PV panel 1.
        The actual value = The receive data.
        The unit of actual value is Watt."
    ::= { pvLoopParameter 71 }
peakPowerOfPVPanel2 OBJECT-TYPE
    SYNTAX INTEGER(1..65535)
    MAX-ACCESS read-write
    STATUS current
    DESCRIPTION "
        The peak power of PV panel 2.
        The actual value = The receive data.
        The unit of actual value is Watt."
    ::= { pvLoopParameter 72 }
peakPowerOfPVPanel3 OBJECT-TYPE
    SYNTAX INTEGER(1..65535)
    MAX-ACCESS read-write
    STATUS current
    DESCRIPTION "
        The peak power of PV panel 3.
        The actual value = The receive data.
        The unit of actual value is Watt."
    ::= { pvLoopParameter 73 }
peakPowerOfPVPanel4 OBJECT-TYPE
    SYNTAX INTEGER(1..65535)
    MAX-ACCESS read-write
    STATUS current
    DESCRIPTION "
        The peak power of PV panel 4.
        The actual value = The receive data.
        The unit of actual value is Watt."
    ::= { pvLoopParameter 74 }
peakPowerOfPVPanel5 OBJECT-TYPE
    SYNTAX INTEGER(1..65535)
    MAX-ACCESS read-write
    STATUS current
    DESCRIPTION "
        The peak power of PV panel 5.
        The actual value = The receive data.
        The unit of actual value is Watt."
    ::= { pvLoopParameter 75 }
peakPowerOfPVPanel6 OBJECT-TYPE
    SYNTAX INTEGER(1..65535)
    MAX-ACCESS read-write
    STATUS current
    DESCRIPTION "
        The peak power of PV panel 6.
        The actual value = The receive data.
        The unit of actual value is Watt."
    ::= { pvLoopParameter 76 }
peakPowerOfPVPanel7 OBJECT-TYPE
    SYNTAX INTEGER(1..65535)
    MAX-ACCESS read-write
    STATUS current
    DESCRIPTION "
        The peak power of PV panel 7.
        The actual value = The receive data.
        The unit of actual value is Watt."
    ::= { pvLoopParameter 77 }
peakPowerOfPVPanel8 OBJECT-TYPE
    SYNTAX INTEGER(1..65535)
    MAX-ACCESS read-write
    STATUS current
    DESCRIPTION "
        The peak power of PV panel 8.
        The actual value = The receive data.
        The unit of actual value is Watt."
    ::= { pvLoopParameter 78 }
peakPowerOfPVPanel9 OBJECT-TYPE
    SYNTAX INTEGER(1..65535)
    MAX-ACCESS read-write
    STATUS current
    DESCRIPTION "
        The peak power of PV panel 9.
        The actual value = The receive data.
        The unit of actual value is Watt."
    ::= { pvLoopParameter 79 }
peakPowerOfPVPanel10 OBJECT-TYPE
    SYNTAX INTEGER(1..65535)
    MAX-ACCESS read-write
    STATUS current
    DESCRIPTION "
        The peak power of PV panel 10.
        The actual value = The receive data.
        The unit of actual value is Watt."
    ::= { pvLoopParameter 80 }
peakPowerOfPVPanel11 OBJECT-TYPE
    SYNTAX INTEGER(1..65535)
    MAX-ACCESS read-write
    STATUS current
    DESCRIPTION "
        The peak power of PV panel 11.
        The actual value = The receive data.
        The unit of actual value is Watt."
    ::= { pvLoopParameter 81 }
peakPowerOfPVPanel12 OBJECT-TYPE
    SYNTAX INTEGER(1..65535)
    MAX-ACCESS read-write
    STATUS current
    DESCRIPTION "
        The peak power of PV panel 12.
        The actual value = The receive data.
        The unit of actual value is Watt."
    ::= { pvLoopParameter 82 }
peakPowerOfPVPanel13 OBJECT-TYPE
    SYNTAX INTEGER(1..65535)
    MAX-ACCESS read-write
    STATUS current
    DESCRIPTION "
        The peak power of PV panel 13.
        The actual value = The receive data.
        The unit of actual value is Watt."
    ::= { pvLoopParameter 83 }
peakPowerOfPVPanel14 OBJECT-TYPE
    SYNTAX INTEGER(1..65535)
    MAX-ACCESS read-write
    STATUS current
    DESCRIPTION "
        The peak power of PV panel 14.
        The actual value = The receive data.
        The unit of actual value is Watt."
    ::= { pvLoopParameter 84 }
peakPowerOfPVPanel15 OBJECT-TYPE
    SYNTAX INTEGER(1..65535)
    MAX-ACCESS read-write
    STATUS current
    DESCRIPTION "
        The peak power of PV panel 15.
        The actual value = The receive data.
        The unit of actual value is Watt."
    ::= { pvLoopParameter 85 }
peakPowerOfPVPanel16 OBJECT-TYPE
    SYNTAX INTEGER(1..65535)
    MAX-ACCESS read-write
    STATUS current
    DESCRIPTION "
        The peak power of PV panel 16.
        The actual value = The receive data.
        The unit of actual value is Watt."
    ::= { pvLoopParameter 86 }
peakPowerOfPVPanel17 OBJECT-TYPE
    SYNTAX INTEGER(1..65535)
    MAX-ACCESS read-write
    STATUS current
    DESCRIPTION "
        The peak power of PV panel 17.
        The actual value = The receive data.
        The unit of actual value is Watt."
    ::= { pvLoopParameter 87 }
peakPowerOfPVPanel18 OBJECT-TYPE
    SYNTAX INTEGER(1..65535)
    MAX-ACCESS read-write
    STATUS current
    DESCRIPTION "
        The peak power of PV panel 18.
        The actual value = The receive data.
        The unit of actual value is Watt."
    ::= { pvLoopParameter 88 }
peakPowerOfPVPanel19 OBJECT-TYPE
    SYNTAX INTEGER(1..65535)
    MAX-ACCESS read-write
    STATUS current
    DESCRIPTION "
        The peak power of PV panel 19.
        The actual value = The receive data.
        The unit of actual value is Watt."
    ::= { pvLoopParameter 89 }
peakPowerOfPVPanel20 OBJECT-TYPE
    SYNTAX INTEGER(1..65535)
    MAX-ACCESS read-write
    STATUS current
    DESCRIPTION "
        The peak power of PV panel 20.
        The actual value = The receive data.
        The unit of actual value is Watt."
    ::= { pvLoopParameter 90 }
peakPowerOfPVPanel21 OBJECT-TYPE
    SYNTAX INTEGER(1..65535)
    MAX-ACCESS read-write
    STATUS current
    DESCRIPTION "
        The peak power of PV panel 21.
        The actual value = The receive data.
        The unit of actual value is Watt."
    ::= { pvLoopParameter 91 }
peakPowerOfPVPanel22 OBJECT-TYPE
    SYNTAX INTEGER(1..65535)
    MAX-ACCESS read-write
    STATUS current
    DESCRIPTION "
        The peak power of PV panel 22.
        The actual value = The receive data.
        The unit of actual value is Watt."
    ::= { pvLoopParameter 92 }
peakPowerOfPVPanel23 OBJECT-TYPE
    SYNTAX INTEGER(1..65535)
    MAX-ACCESS read-write
    STATUS current
    DESCRIPTION "
        The peak power of PV panel 23.
        The actual value = The receive data.
        The unit of actual value is Watt."
    ::= { pvLoopParameter 93 }
peakPowerOfPVPanel24 OBJECT-TYPE
    SYNTAX INTEGER(1..65535)
    MAX-ACCESS read-write
    STATUS current
    DESCRIPTION "
        The peak power of PV panel 24.
        The actual value = The receive data.
        The unit of actual value is Watt."
    ::= { pvLoopParameter 94 }
peakPowerOfPVPanel25 OBJECT-TYPE
    SYNTAX INTEGER(1..65535)
    MAX-ACCESS read-write
    STATUS current
    DESCRIPTION "
        The peak power of PV panel 25.
        The actual value = The receive data.
        The unit of actual value is Watt."
    ::= { pvLoopParameter 95 }
peakPowerOfPVPanel26 OBJECT-TYPE
    SYNTAX INTEGER(1..65535)
    MAX-ACCESS read-write
    STATUS current
    DESCRIPTION "
        The peak power of PV panel 26.
        The actual value = The receive data.
        The unit of actual value is Watt."
    ::= { pvLoopParameter 96 }
peakPowerOfPVPanel27 OBJECT-TYPE
    SYNTAX INTEGER(1..65535)
    MAX-ACCESS read-write
    STATUS current
    DESCRIPTION "
        The peak power of PV panel 27.
        The actual value = The receive data.
        The unit of actual value is Watt."
    ::= { pvLoopParameter 97 }
peakPowerOfPVPanel28 OBJECT-TYPE
    SYNTAX INTEGER(1..65535)
    MAX-ACCESS read-write
    STATUS current
    DESCRIPTION "
        The peak power of PV panel 28.
        The actual value = The receive data.
        The unit of actual value is Watt."
    ::= { pvLoopParameter 98 }
peakPowerOfPVPanel29 OBJECT-TYPE
    SYNTAX INTEGER(1..65535)
    MAX-ACCESS read-write
    STATUS current
    DESCRIPTION "
        The peak power of PV panel 29.
        The actual value = The receive data.
        The unit of actual value is Watt."
    ::= { pvLoopParameter 99 }
peakPowerOfPVPanel30 OBJECT-TYPE
    SYNTAX INTEGER(1..65535)
    MAX-ACCESS read-write
    STATUS current
    DESCRIPTION "
        The peak power of PV panel 30.
        The actual value = The receive data.
        The unit of actual value is Watt."
    ::= { pvLoopParameter 100 }
peakPowerOfPVPanel31 OBJECT-TYPE
    SYNTAX INTEGER(1..65535)
    MAX-ACCESS read-write
    STATUS current
    DESCRIPTION "
        The peak power of PV panel 31.
        The actual value = The receive data.
        The unit of actual value is Watt."
    ::= { pvLoopParameter 101 }
peakPowerOfPVPanel32 OBJECT-TYPE
    SYNTAX INTEGER(1..65535)
    MAX-ACCESS read-write
    STATUS current
    DESCRIPTION "
        The peak power of PV panel 32.
        The actual value = The receive data.
        The unit of actual value is Watt."
    ::= { pvLoopParameter 102 }
 
 
 
---System Alarm
systemAlarm OBJECT IDENTIFIER ::= { dpcDistributedPower 4 }

------------------------------------------------------------
-- Alarm trap counter { systemAlarm 1 }
------------------------------------------------------------

totalAlarmNumber OBJECT-TYPE
    SYNTAX Counter32
    MAX-ACCESS read-only
    STATUS current
    DESCRIPTION "
        The total number of the current alarm."
    ::= { systemAlarm 1 }
        
------------------------------------------------------------
-- Active Alarm table { systemAlarm 2 }
------------------------------------------------------------

activeAlarmTable OBJECT-TYPE
    SYNTAX SEQUENCE OF ActiveAlarmEntry
    MAX-ACCESS not-accessible
    STATUS current
    DESCRIPTION "
        Table holding information about the currently active alarms."
    ::= { systemAlarm 2 }

activeAlarmEntry OBJECT-TYPE
    SYNTAX ActiveAlarmEntry
    MAX-ACCESS not-accessible
    STATUS current
    DESCRIPTION "
        An entry (conceptual row) in the alarmTrapTable."
    INDEX { alarmIndex }
    ::= { activeAlarmTable 1 }

ActiveAlarmEntry ::= SEQUENCE {
    alarmIndex Counter32,
    alarmTime DisplayString,
    alarmLevel Integer32,
    alarmType Integer32,
    alarmRelateDOPosition Integer32,
    alarmRelateDO Integer32,
    alarmBuzzer Integer32,
    alarmMoudleID Integer32,
    alarmStatusChange Integer32,
    alarmName DisplayString,
    }

alarmIndex OBJECT-TYPE
    SYNTAX Counter32 {
        ac1SlightOverCurrent (0),
        ac1SevereOvercurrent  (1),
        ac1OverVoltage (2),
        ac1UnderVoltage (3),
        ac1Phasefailure (4),
        ac1Mainsfailure (5),
        ac1HighFrequency  (6),
        ac1LowFrequency  (7),
        ac2SlightOverCurrent (8),
        ac2SevereOverCurrent (9),
        ac2OverVoltage (10),
        ac2UnderVoltage (11),
        ac2LosePhase (12),
        ac2Mainsfailure (13),
        ac2FreqHigh (14),
        ac2FreqLow (15),
        acSPDFault (16),
        acSPDMCBFault (17),
        acTrip (18),
        acSampleBoardFault (19),
        acControllerEEPROMFault (20),
        dg1Repairing (21),
        dg2Repairing (22),

        dcOverVoltage (86),
        dcHighVoltage (87),
        dcLowVoltage (88),
        dcUnderVoltage (89),
        ecoRunning (90),
        busInsulationFault (91),
        loadBranchInsulationFault (92),
        dcTotalLoadSlightOverCurrent (93),
        dcTotalLoadSevereOverCurrent (94),
        systemSPDFault (95),
        systemTotalAlarm (96),
        
        sc210-1CommunicationFault (156),
        sc210-2CommunicationFault (157),
        sc501-1CommunicationFault (158),
        sc501-2CommunicationFault (159),
        sc501-3CommunicationFault (160),
        sc501-4CommunicationFault (161),
        sc310-1CommunicationFault (162),
        sc310-2CommunicationFault (163),
        sc310-3CommunicationFault (164),
        sc340-1CommunicationFault (165),
        sc340-2CommunicationFault (166),
        sc340-3CommunicationFault (167),
        sc200-1CommunicationFault (168),
        sc200-2CommunicationFault (169),
        sc200-3CommunicationFault (170),
        sc920-1CommunicationFault (171),
        sc920-2CommunicationFault (172),
        sc320-1CommunicationFault (173),
        sc320-2CommunicationFault (174),
        sc320-3CommunicationFault (175),
        sc320-4CommunicationFault (176),
        sc320-5CommunicationFault (177),
        sc330-1CommunicationFault (178),
        sc330-2CommunicationFault (179),
        sc330-3CommunicationFault (180),
        sc330-4CommunicationFault (181),
        sc330-5CommunicationFault (182),
        sc930-1CommunicationFault (183),
        sc930-2CommunicationFault (184),
        sc900-1CommunicationFault (185),
        sc900-2CommunicationFault (186),
        sc900-3CommunicationFault (187),
        sc900-4CommunicationFault (188),
        bms1CommunicationFault (189),
        bms2CommunicationFault (190),
        bms3CommunicationFault (191),
        bms4CommunicationFault (192),
        bms5CommunicationFault (193),
        bms6CommunicationFault (194),
        bms7CommunicationFault (195),
        bms8CommunicationFault (196),
        bms9CommunicationFault (197),
        bms10CommunicationFault (198),
        bms11CommunicationFault (199),
        bms12CommunicationFault (200),
        bms13CommunicationFault (201),
        bms14CommunicationFault (202),
        bms15CommunicationFault (203),
        bms16CommunicationFault (204),
        bms17CommunicationFault (205),
        bms18CommunicationFault (206),
        bms19CommunicationFault (207),
        bms20CommunicationFault (208),
        temperatureSensor1NotAssemble (209),
        temperatureSensor2NotAssemble (210),
        extend1TemperatureSensor1NotAssemble (211),
        extend1TemperatureSensor2NotAssemble (212),
        bmm1CommunicationFault  (213),
        bmm2CommunicationFault  (214),
        bmm3CommunicationFault  (215),
        bmm4CommunicationFault  (216),
        bmm5CommunicationFault  (217),
        bmm6CommunicationFault  (218),
        bmm7CommunicationFault  (219),
        bmm8CommunicationFault  (220),
        bmm9CommunicationFault  (221),
        bmm10CommunicationFault (222),
        dg1Communicationfault   (223),
        dg2Communicationfault   (224),
        dg3Communicationfault   (225),
        extend2TemperatureSensor1NotAssemble    (226),
        extend2TemperatureSensor2NotAssemble    (227),
        extend3TemperatureSensor1NotAssemble    (228),
        extend3TemperatureSensor2NotAssemble    (229),
        extend4TemperatureSensor1NotAssemble    (230),
        extend4TemperatureSensor2NotAssemble    (231),
        extend5TemperatureSensor1NotAssemble    (232),
        extend5TemperatureSensor2NotAssemble    (233),
        sc350-1CommunicationFault (234),
        sc350-2CommunicationFault (235),
        sc350-3CommunicationFault (236),
        
        lLVD1 (252),
        lLVD2 (253),
        lLVD3 (254),
        lLVD4 (255),
        lLVD5 (256),
        lLVD6 (257),
        lLVD7 (258),
        lLVD8 (259),
        bLVD (260),
        lLVD1Fail (261),
        lLVD2Fail (262),
        lLVD3Fail (263),
        lLVD4Fail (264),
        lLVD5Fail (265),
        lLVD6Fail (266),
        lLVD7Fail (267),
        lLVD8Fail (268),
        bLVDFail (269),
        preAlarmlLVD1 (270),
        preAlarmlLVD2 (271),
        preAlarmlLVD3 (272),
        preAlarmlLVD4 (273),
        preAlarmlLVD5 (274),
        preAlarmlLVD6 (275),
        preAlarmlLVD7 (276),
        preAlarmlLVD8 (277),
        preAlarmbLVD (278),

        battery1Break (333),
        battery2Break (334),
        battery3Break (335),
        battery4Break (336),
        battery5Break (337),
        battery6Break (338),
        battery7Break (339),
        battery8Break (340),
        
        battery1NegtiveBreak (404),
        battery2NegtiveBreak (405),
        battery3NegtiveBreak (406),
        battery4NegtiveBreak (407),
        battery5NegtiveBreak (408),
        battery6NegtiveBreak (409),
        battery7NegtiveBreak (410),
        battery8NegtiveBreak (411),
        
        batteryChargeOverCurrent (475),
        batteryDischarge (476),
        batteryQuickTestOverCurrent (477),
        battery1MiddleImbalance (478),
        battery2MiddleImbalance (479),
        battery3MiddleImbalance (480),
        battery4MiddleImbalance (481),
        battery5MiddleImbalance (482),
        battery6MiddleImbalance (483),
        battery7MiddleImbalance (484),
        battery8MiddleImbalance (485),
        battery1CannotCharge (486),
        battery2CannotCharge (487),
        battery3CannotCharge (488),
        battery4CannotCharge (489),
        battery5CannotCharge (490),
        battery6CannotCharge (491),
        battery7CannotCharge (492),
        battery8CannotCharge (493),
        batteryTestFail (494),

        dcBranch1SlightOverCurrent (549),
        dcBranch2SlightOverCurrent (550),
        dcBranch3SlightOverCurrent (551),
        dcBranch4SlightOverCurrent (552),
        dcBranch5SlightOverCurrent (553),
        dcBranch6SlightOverCurrent (554),
        dcBranch7SlightOverCurrent (555),
        dcBranch8SlightOverCurrent (556),
        dcBranch9SlightOverCurrent (557),
        dcBranch10SlightOverCurrent (558),
        dcBranch11SlightOverCurrent (559),
        dcBranch12SlightOverCurrent (560),
        dcBranch13SlightOverCurrent (561),
        dcBranch14SlightOverCurrent (562),
        dcBranch15SlightOverCurrent (563),
        dcBranch16SlightOverCurrent (564),
        dcBranch17SlightOverCurrent (565),
        dcBranch18SlightOverCurrent (566),
        dcBranch19SlightOverCurrent (567),
        dcBranch20SlightOverCurrent (568),
        dcBranch21SlightOverCurrent (569),
        dcBranch22SlightOverCurrent (570),
        dcBranch23SlightOverCurrent (571),
        dcBranch24SlightOverCurrent (572),
        dcBranch25SlightOverCurrent (573),
        dcBranch26SlightOverCurrent (574),
        dcBranch27SlightOverCurrent (575),
        dcBranch28SlightOverCurrent (576),
        dcBranch29SlightOverCurrent (577),
        dcBranch30SlightOverCurrent (578),
        dcBranch31SlightOverCurrent (579),
        dcBranch32SlightOverCurrent (580),
        dcBranch33SlightOverCurrent (581),
        dcBranch34SlightOverCurrent (582),
        dcBranch35SlightOverCurrent (583),
        dcBranch36SlightOverCurrent (584),
        dcBranch37SlightOverCurrent (585),
        dcBranch38SlightOverCurrent (586),
        dcBranch39SlightOverCurrent (587),
        dcBranch40SlightOverCurrent (588),
        dcBranch41SlightOverCurrent (589),
        dcBranch42SlightOverCurrent (590),
        dcBranch43SlightOverCurrent (591),
        dcBranch44SlightOverCurrent (592),
        dcBranch45SlightOverCurrent (593),
        dcBranch46SlightOverCurrent (594),
        dcBranch47SlightOverCurrent (595),
        dcBranch48SlightOverCurrent (596),
        dcBranch49SlightOverCurrent (597),
        dcBranch50SlightOverCurrent (598),
        dcBranch51SlightOverCurrent (599),
        dcBranch52SlightOverCurrent (600),
        dcBranch53SlightOverCurrent (601),
        dcBranch54SlightOverCurrent (602),
        dcBranch55SlightOverCurrent (603),
        dcBranch56SlightOverCurrent (604),
        dcBranch57SlightOverCurrent (605),
        dcBranch58SlightOverCurrent (606),
        dcBranch59SlightOverCurrent (607),
        dcBranch60SlightOverCurrent (608),
        dcBranch61SlightOverCurrent (609),
        dcBranch62SlightOverCurrent (610),
        dcBranch63SlightOverCurrent (611),
        dcBranch64SlightOverCurrent (612),
        dcBranch65SlightOverCurrent (613),
        dcBranch66SlightOverCurrent (614),
        dcBranch67SlightOverCurrent (615),
        dcBranch68SlightOverCurrent (616),
        dcBranch69SlightOverCurrent (617),
        dcBranch70SlightOverCurrent (618),
        dcBranch71SlightOverCurrent (619),
        dcBranch72SlightOverCurrent (620),
        
        dcBranch1SevereOverCurrent (684),
        dcBranch2SevereOverCurrent (685),
        dcBranch3SevereOverCurrent (686),
        dcBranch4SevereOverCurrent (687),
        dcBranch5SevereOverCurrent (688),
        dcBranch6SevereOverCurrent (689),
        dcBranch7SevereOverCurrent (690),
        dcBranch8SevereOverCurrent (691),
        dcBranch9SevereOverCurrent (692),
        dcBranch10SevereOverCurrent (693),
        dcBranch11SevereOverCurrent (694),
        dcBranch12SevereOverCurrent (695),
        dcBranch13SevereOverCurrent (696),
        dcBranch14SevereOverCurrent (697),
        dcBranch15SevereOverCurrent (698),
        dcBranch16SevereOverCurrent (699),
        dcBranch17SevereOverCurrent (700),
        dcBranch18SevereOverCurrent (701),
        dcBranch19SevereOverCurrent (702),
        dcBranch20SevereOverCurrent (703),
        dcBranch21SevereOverCurrent (704),
        dcBranch22SevereOverCurrent (705),
        dcBranch23SevereOverCurrent (706),
        dcBranch24SevereOverCurrent (707),
        dcBranch25SevereOverCurrent (708),
        dcBranch26SevereOverCurrent (709),
        dcBranch27SevereOverCurrent (710),
        dcBranch28SevereOverCurrent (711),
        dcBranch29SevereOverCurrent (712),
        dcBranch30SevereOverCurrent (713),
        dcBranch31SevereOverCurrent (714),
        dcBranch32SevereOverCurrent (715),
        dcBranch33SevereOverCurrent (716),
        dcBranch34SevereOverCurrent (717),
        dcBranch35SevereOverCurrent (718),
        dcBranch36SevereOverCurrent (719),
        dcBranch37SevereOverCurrent (720),
        dcBranch38SevereOverCurrent (721),
        dcBranch39SevereOverCurrent (722),
        dcBranch40SevereOverCurrent (723),
        dcBranch41SevereOverCurrent (724),
        dcBranch42SevereOverCurrent (725),
        dcBranch43SevereOverCurrent (726),
        dcBranch44SevereOverCurrent (727),
        dcBranch45SevereOverCurrent (728),
        dcBranch46SevereOverCurrent (729),
        dcBranch47SevereOverCurrent (730),
        dcBranch48SevereOverCurrent (731),
        dcBranch49SevereOverCurrent (732),
        dcBranch50SevereOverCurrent (733),
        dcBranch51SevereOverCurrent (734),
        dcBranch52SevereOverCurrent (735),
        dcBranch53SevereOverCurrent (736),
        dcBranch54SevereOverCurrent (737),
        dcBranch55SevereOverCurrent (738),
        dcBranch56SevereOverCurrent (739),
        dcBranch57SevereOverCurrent (740),
        dcBranch58SevereOverCurrent (741),
        dcBranch59SevereOverCurrent (742),
        dcBranch60SevereOverCurrent (743),
        dcBranch61SevereOverCurrent (744),
        dcBranch62SevereOverCurrent (745),
        dcBranch63SevereOverCurrent (746),
        dcBranch64SevereOverCurrent (747),
        dcBranch65SevereOverCurrent (748),
        dcBranch66SevereOverCurrent (749),
        dcBranch67SevereOverCurrent (750),
        dcBranch68SevereOverCurrent (751),
        dcBranch69SevereOverCurrent (752),
        dcBranch70SevereOverCurrent (753),
        dcBranch71SevereOverCurrent (754),
        dcBranch72SevereOverCurrent (755),

        loadBreak (819),
        load1Break (820),
        load2Break (821),
        load3Break (822),
        load4Break (823),
        load5Break (824),
        load6Break (825),
        load7Break (826),
        load8Break (827),
        load9Break (828),
        load10Break (829),
        load11Break (830),
        load12Break (831),
        load13Break (832),
        load14Break (833),
        load15Break (834),
        load16Break (835),
        load17Break (836),
        load18Break (837),
        load19Break (838),
        load20Break (839),
        load21Break (840),
        load22Break (841),
        load23Break (842),
        load24Break (843),
        load25Break (844),
        load26Break (845),
        load27Break (846),
        load28Break (847),
        load29Break (848),
        load30Break (849),
        load31Break (850),
        load32Break (851),
        load33Break (852),
        load34Break (853),
        load35Break (854),
        load36Break (855),
        load37Break (856),
        load38Break (857),
        load39Break (858),
        load40Break (859),
        load41Break (860),
        load42Break (861),
        load43Break (862),
        load44Break (863),
        load45Break (864),
        load46Break (865),
        load47Break (866),
        load48Break (867),
        load49Break (868),
        load50Break (869),
        load51Break (870),
        load52Break (871),
        load53Break (872),
        load54Break (873),
        load55Break (874),
        load56Break (875),
        load57Break (876),
        load58Break (877),
        load59Break (878),
        load60Break (879),
        load61Break (880),
        load62Break (881),
        load63Break (882),
        load64Break (883),
        load65Break (884),
        load66Break (885),
        load67Break (886),
        load68Break (887),
        load69Break (888),
        load70Break (889),
        load71Break (890),
        load72Break (891),

        ambientTemperature1High1(1525),
        ambientTemperature2High1(1526),
        ambientTemperature3High1(1527),
        ambientTemperature4High1(1528),
        ambientTemperature5High1(1529),
        ambientTemperature6High1(1530),
        ambientTemperature7High1(1531),
        ambientTemperature8High1(1532),
        ambientTemperature1High2(1533),
        ambientTemperature2High2(1534),
        ambientTemperature3High2(1535),
        ambientTemperature4High2(1536),
        ambientTemperature5High2(1537),
        ambientTemperature6High2(1538),
        ambientTemperature7High2(1539),
        ambientTemperature8High2(1540),
        ambientTemperature1Low1(1541),
        ambientTemperature2Low1(1542),
        ambientTemperature3Low1(1543),
        ambientTemperature4Low1(1544),
        ambientTemperature5Low1(1545),
        ambientTemperature6Low1(1546),
        ambientTemperature7Low1(1547),
        ambientTemperature8Low1(1548),
        ambientTemperature1Low2(1549),
        ambientTemperature2Low2(1550),
        ambientTemperature3Low2(1551),
        ambientTemperature4Low2(1552),
        ambientTemperature5Low2(1553),
        ambientTemperature6Low2(1554),
        ambientTemperature7Low2(1555),
        ambientTemperature8Low2(1556),
        humidityHigh(1557),
        humidityLow(1558),
        
        batteryTemperature1High1(1620),
        batteryTemperature2High1(1621),
        batteryTemperature3High1(1622),
        batteryTemperature4High1(1623),
        batteryTemperature5High1(1624),
        batteryTemperature6High1(1625),
        batteryTemperature7High1(1626),
        batteryTemperature8High1(1627),
        batteryTemperature1High2(1628),
        batteryTemperature2High2(1629),
        batteryTemperature3High2(1630),
        batteryTemperature4High2(1631),
        batteryTemperature5High2(1632),
        batteryTemperature6High2(1633),
        batteryTemperature7High2(1634),
        batteryTemperature8High2(1635),
        batteryTemperature1Low1(1636),
        batteryTemperature2Low1(1637),
        batteryTemperature3Low1(1638),
        batteryTemperature4Low1(1639),
        batteryTemperature5Low1(1640),
        batteryTemperature6Low1(1641),
        batteryTemperature7Low1(1642),
        batteryTemperature8Low1(1643),
        batteryTemperature1Low2(1644),
        batteryTemperature2Low2(1645),
        batteryTemperature3Low2(1646),
        batteryTemperature4Low2(1647),
        batteryTemperature5Low2(1648),
        batteryTemperature6Low2(1649),
        batteryTemperature7Low2(1650),
        batteryTemperature8Low2(1651),
        bTRMHigh1(1652),
        bTRMHigh2(1653),

        digitalInput1Alarm(1715),
        digitalInput2Alarm(1716),
        digitalInput3Alarm(1717),
        digitalInput4Alarm(1718),
        digitalInput5Alarm(1719),
        digitalInput6Alarm(1720),
        extend1digitalInput1Alarm(1721),
        extend1digitalInput2Alarm(1722),
        extend1digitalInput3Alarm(1723),
        extend1digitalInput4Alarm(1724),
        extend1digitalInput5Alarm(1725),
        extend1digitalInput6Alarm(1726),
        extend1digitalInput7Alarm(1727),
        extend1digitalInput8Alarm(1728),
        extend2digitalInput1Alarm(1729),
        extend2digitalInput2Alarm(1730),
        extend2digitalInput3Alarm(1731),
        extend2digitalInput4Alarm(1732),
        extend2digitalInput5Alarm(1733),
        extend2digitalInput6Alarm(1734),
        extend2digitalInput7Alarm(1735),
        extend2digitalInput8Alarm(1736),
        extend3digitalInput1Alarm(1737),
        extend3digitalInput2Alarm(1738),
        extend3digitalInput3Alarm(1739),
        extend3digitalInput4Alarm(1740),
        extend3digitalInput5Alarm(1741),
        extend3digitalInput6Alarm(1742),
        extend3digitalInput7Alarm(1743),
        extend3digitalInput8Alarm(1744),
        extend4digitalInput1Alarm(1745),
        extend4digitalInput2Alarm(1746),
        extend4digitalInput3Alarm(1747),
        extend4digitalInput4Alarm(1748),
        extend4digitalInput5Alarm(1749),
        extend4digitalInput6Alarm(1750),
        extend4digitalInput7Alarm(1751),
        extend4digitalInput8Alarm(1752),
        extend5digitalInput1Alarm(1753),
        extend5digitalInput2Alarm(1754),
        extend5digitalInput3Alarm(1755),
        extend5digitalInput4Alarm(1756),
        extend5digitalInput5Alarm(1757),
        extend5digitalInput6Alarm(1758),
        extend5digitalInput7Alarm(1759),
        extend5digitalInput8Alarm(1760),
        
        rectifierCurrentSampleFault(2042),
        rectifierPrimarySideCircuitShort(2043),
        mutipleRectifierNoOutput(2044),
        singleRectifierNooutput(2045),
        rectifierOutsideCircuitShort(2046),
        rectifierPFCImbalance(2047),
        rectifierIdentifyFault(2048),
        rectifierLost(2049),
        rectifierCurrentSharingSlightlyFault(2050),
        rectifierCurrentSharingSevereFault(2051),
        rectifierNoPosition(2052),
        rectifierOutputOverCurrent(2053),
        rectifierE2PROMFault(2054),
        rectifierCANCommunicationFault(2055),
        rectifierSecondSideCommmunicationFault(2056),
        rectifierPrimarySideCommmunicationFault(2057),
        rectifierFanFault(2058),
        rectifierStartResistorBreak(2059),
        rectifierPFCOvervoltageProtection(2060),
        rectifierPFCUndervoltageProtection(2061),
        rectifierACImbalance(2062),
        rectifierACLosePhase(2063),
        rectifierACUnderVoltageProtection(2064),
        rectifierACOverVoltageProtection(2065),
        rectifierInternalCircuitShort(2066),
        rectifierOutputFuseBreak(2067),
        rectifierSecondaryHotPointOverTemperature(2068),
        rectifierPrimaryHotPointOverTemperature(2069),
        rectifierAmbientOverTemperature(2070),
        rectifierOutputUnderVoltageProtection(2071),
        rectifierOuterOverVoltageProtection(2072),
        rectifierInternalOverVoltageProtection(2073),
        rectifierPFCShort(2074),
        rectifierOVSD(2075),
        rectifierSecurityCodeError(2076),
        
        rectifierSingleFault(2090),
        rectifierMutipleFault(2091),
        
        solarControllerPrimaryCalibrateFault    (2137),
        solarControllerSingleNooutput(2138),
        solarControllerOutsideCircuitShort  (2139),
        solarControllerLost (2140),
        solarControllerNoPosition   (2141),
        solarControllerOutputOverCurrent(2142),
        solarControllerE2PROMFault(2143),
        solarControllerCANCommunicationFault(2144),
        solarControllerSecondSideCommmunicationFault(2145),
        solarControllerPrimarySideCommmunicationFault   (2146),
        solarControllerFanFault (2147),
        solarControllerPFCOvervoltageProtection(2148),
        solarControllerPFCUndervoltageProtection(2149),
        solarControllerInputUnderVoltageProtection  (2150),
        solarControllerInputOverVoltageProtection   (2151),
        solarControllerInternalCircuitShort (2152),
        solarControllerSecondaryHotPointOverTemperature (2153),
        solarControllerAmbientOverTemperature   (2154),
        solarControllerOuterOverVoltageProtection   (2155),
        solarControllerInternalOverVoltageProtection    (2156),
        solarControllerSecurityCodeError    (2157),
        solarControllerPVPowerLack  (2158),
        solarControllerPVLoopFault  (2159),

        solarControllerSingleFault  (2185),
        solarControllerMutipleFault (2186),

        dcdcConverterCurrentSampleFault (2422),
        dcdcConverterPrimary-SideCircuitShort   (2423),
        dcdcConverterMutipleRectifierNoOutput(2424),
        dcdcConverterSingleRectifierNooutput(2425),
        dcdcConverterOutsideCircuitShort    (2426),
        dcdcConverterPFCImbalance   (2427),
        dcdcConverterIdentifyFault  (2428),
        dcdcConverterLost   (2429),
        dcdcConverterCurrentSharingSlightlyFault    (2430),
        dcdcConverterCurrentSharingSevereFault  (2431),
        dcdcConverterNoPosition (2432),
        dcdcConverterOutputOverCurrent  (2433),
        dcdcConverterE2PROMFault(2434),
        dcdcConverterCANCommunicationFault  (2435),
        dcdcConverterSecondSideCommmunicationFault  (2436),
        dcdcConverterPrimarySideCommmunicationFault (2437),
        dcdcConverterFanFault   (2438),
        dcdcConverterStartResistorBreak (2439),
        dcdcConverterPFCOvervoltageProtection(2440),
        dcdcConverterPFCUndervoltageProtection(2441),
        dcdcConverterACImbalance    (2442),
        dcdcConverterACLosePhase    (2443),
        dcdcConverterInputUnderVoltageProtection    (2444),
        dcdcConverterInputOverVoltageProtection (2445),
        dcdcConverterInternalCircuitShort   (2446),
        dcdcConverterOutputFuseBreak    (2447),
        dcdcConverterSecondaryHotPointOverTemperature   (2448),
        dcdcConverterPrimaryHotPointOverTemperature (2449),
        dcdcConverterAmbientOverTemperature(2450),
        dcdcConverterOutputUnderVoltageProtection(2451),
        dcdcConverterOuterOverVoltageProtection(2452),
        dcdcConverterInternalOverVoltageProtection(2453),
        dcdcConverterPFCShort   (2454),
        dcdcConverterOVSD   (2455),
        dcdcConverterSecurityCodeError  (2456),

        dcdcConverterSingleFault    (2470),
        dcdcConverterMutipleFault   (2471),

        bmsTotalAlarm(2502),
        bmsBatteryOverCurrent(2503),
        bmsBatteryPacksOverVoltage(2504),
        bmsBatteryPacksUnderVoltage(2505),
        bmsBatteryCellOverVoltage(2506),
        bmsBatteryCellUnderVoltage(2507),
        bmsBatteryHighTenmperature(2508),
        bmsBatteryLowTenmperature(2509),
        bmsBatteryOutputShort(2510),
        bmsBatteryLowSOC(2511),
        
        plcArithmetic1Alarm(2575),
        plcArithmetic2Alarm(2576),
        plcArithmetic3Alarm(2577),
        plcArithmetic4Alarm(2578),
        plcArithmetic5Alarm(2579),
        plcArithmetic6Alarm(2580),
        plcArithmetic7Alarm(2581),
        plcArithmetic8Alarm(2582),
        plcArithmetic9Alarm(2583),
        plcArithmetic10Alarm(2584),
        plcArithmetic11Alarm(2585),
        plcArithmetic12Alarm(2586),
        plcArithmetic13Alarm(2587),
        plcArithmetic14Alarm(2588),
        plcArithmetic15Alarm(2589),
        plcArithmetic16Alarm(2590),
        plcArithmetic17Alarm(2591),
        plcArithmetic18Alarm(2592),
        plcArithmetic19Alarm(2593),
        plcArithmetic20Alarm(2594),
        plcArithmetic21Alarm(2595),
        plcArithmetic22Alarm(2596),
        plcArithmetic23Alarm(2597),
        plcArithmetic24Alarm(2598),
        plcArithmetic25Alarm(2599),
        plcArithmetic26Alarm(2600),
        plcArithmetic27Alarm(2601),
        plcArithmetic28Alarm(2602),
        plcArithmetic29Alarm(2603),
        plcArithmetic30Alarm(2604),
        plcArithmetic31Alarm(2605),
        plcArithmetic32Alarm(2606),
        plcArithmetic33Alarm(2607),
        plcArithmetic34Alarm(2608),
        plcArithmetic35Alarm(2609),
        plcArithmetic36Alarm(2610),
        plcArithmetic37Alarm(2611),
        plcArithmetic38Alarm(2612),
        plcArithmetic39Alarm(2613),
        plcArithmetic40Alarm(2614),
        
        plcLogic1Alarm(2646),
        plcLogic2Alarm(2647),
        plcLogic3Alarm(2648),
        plcLogic4Alarm(2649),
        plcLogic5Alarm(2650),
        plcLogic6Alarm(2651),
        plcLogic7Alarm(2652),
        plcLogic8Alarm(2653),
        plcLogic9Alarm(2654),
        plcLogic10Alarm(2655),
        
        plcGroup1Alarm(2687),
        plcGroup2Alarm(2688),
        plcGroup3Alarm(2689),
        plcGroup4Alarm(2690),
        plcGroup5Alarm(2691),
        plcGroup6Alarm(2692),
        plcGroup7Alarm(2693),
        plcGroup8Alarm(2694),
        plcGroup9Alarm(2695),
        plcGroup10Alarm(2696),
        plcGroup11Alarm(2697),
        plcGroup12Alarm(2698),
        plcGroup13Alarm(2699),
        plcGroup14Alarm(2700),
        plcGroup15Alarm(2701),
        plcGroup16Alarm(2702),
        plcGroup17Alarm(2703),
        plcGroup18Alarm(2704),
        plcGroup19Alarm(2705),
        plcGroup20Alarm(2706),
        plcGroup21Alarm(2707),
        plcGroup22Alarm(2708),
        plcGroup23Alarm(2709),
        plcGroup24Alarm(2710),
        plcGroup25Alarm(2711),
        plcGroup26Alarm(2712),
        plcGroup27Alarm(2713),
        plcGroup28Alarm(2714),
        plcGroup29Alarm(2715),
        plcGroup30Alarm(2716),
        bmm-TotalAlarm(2780),
        bmm-BatteryOverCurrent(2781),
        bmm-BatteryPacksOverVoltage(2782),
        bmm-BatteryPacksUnderVoltage(2783),
        bmm-BatteryCellOverVoltage(2784),
        bmm-BatteryCellUnderVoltage(2785),
        bmm-BatteryHighTenmperature(2786),
        bmm-BatteryLowTenmperature(2787),
        bmm-BatteryHighResistance(2788),
        
        userAlarm1  (2853),
        userAlarm2  (2854),
        userAlarm3  (2855),
        userAlarm4  (2856),
        userAlarm5  (2857),
        userAlarm6  (2858),
        userAlarm7  (2859),
        userAlarm8  (2860),
        userAlarm9  (2861),
        userAlarm10 (2862),
        userAlarm11 (2863),
        userAlarm12 (2864),
        userAlarm13 (2865),
        userAlarm14 (2866),
        userAlarm15 (2867),
        userAlarm16 (2868),

        dgTotalAlarm    (2932),
        dgEmergencyStop (2933),
        dgStartFail (2934),
        dgStopFail  (2935),
        dgOilPressureLow    (2936),
        dgEngineTemperatureHigh (2937),
        dgOverSpeed (2938),
        dgUnderSpeed    (2939),
        dgOverLoad  (2940),
        dgFuelLevelLow  (2941),
        
        sc350_1Alarm    (3005),
        sc350_2Alarm    (3006),
        sc350_3Alarm    (3007)

    }
    MAX-ACCESS read-only
    STATUS current
    DESCRIPTION "
        The unique sequence number of this alarm trap.
        ac1SlightOverCurrent (0),
        ac1SevereOvercurrent  (1),
        ac1OverVoltage (2),
        ac1UnderVoltage (3),
        ac1Phasefailure (4),
        ac1Mainsfailure (5),
        ac1HighFrequency  (6),
        ac1LowFrequency  (7),
        ac2SlightOverCurrent (8),
        ac2SevereOverCurrent (9),
        ac2OverVoltage (10),
        ac2UnderVoltage (11),
        ac2LosePhase (12),
        ac2Mainsfailure (13),
        ac2FreqHigh (14),
        ac2FreqLow (15),
        acSPDFault (16),
        acSPDMCBFault (17),
        acTrip (18),
        acSampleBoardFault (19),
        acControllerEEPROMFault (20),
        dg1Repairing (21),
        dg2Repairing (22),

        dcOverVoltage (86),
        dcHighVoltage (87),
        dcLowVoltage (88),
        dcUnderVoltage (89),
        ecoRunning (90),
        busInsulationFault (91),
        loadBranchInsulationFault (92),
        dcTotalLoadSlightOverCurrent (93),
        dcTotalLoadSevereOverCurrent (94),
        systemSPDFault (95),
        systemTotalAlarm (96),
        
        sc210-1CommunicationFault (156),
        sc210-2CommunicationFault (157),
        sc501-1CommunicationFault (158),
        sc501-2CommunicationFault (159),
        sc501-3CommunicationFault (160),
        sc501-4CommunicationFault (161),
        sc310-1CommunicationFault (162),
        sc310-2CommunicationFault (163),
        sc310-3CommunicationFault (164),
        sc340-1CommunicationFault (165),
        sc340-2CommunicationFault (166),
        sc340-3CommunicationFault (167),
        sc200-1CommunicationFault (168),
        sc200-2CommunicationFault (169),
        sc200-3CommunicationFault (170),
        sc920-1CommunicationFault (171),
        sc920-2CommunicationFault (172),
        sc320-1CommunicationFault (173),
        sc320-2CommunicationFault (174),
        sc320-3CommunicationFault (175),
        sc320-4CommunicationFault (176),
        sc320-5CommunicationFault (177),
        sc330-1CommunicationFault (178),
        sc330-2CommunicationFault (179),
        sc330-3CommunicationFault (180),
        sc330-4CommunicationFault (181),
        sc330-5CommunicationFault (182),
        sc930-1CommunicationFault (183),
        sc930-2CommunicationFault (184),
        sc900-1CommunicationFault (185),
        sc900-2CommunicationFault (186),
        sc900-3CommunicationFault (187),
        sc900-4CommunicationFault (188),
        bms1CommunicationFault (189),
        bms2CommunicationFault (190),
        bms3CommunicationFault (191),
        bms4CommunicationFault (192),
        bms5CommunicationFault (193),
        bms6CommunicationFault (194),
        bms7CommunicationFault (195),
        bms8CommunicationFault (196),
        bms9CommunicationFault (197),
        bms10CommunicationFault (198),
        bms11CommunicationFault (199),
        bms12CommunicationFault (200),
        bms13CommunicationFault (201),
        bms14CommunicationFault (202),
        bms15CommunicationFault (203),
        bms16CommunicationFault (204),
        bms17CommunicationFault (205),
        bms18CommunicationFault (206),
        bms19CommunicationFault (207),
        bms20CommunicationFault (208),
        temperatureSensor1NotAssemble (209),
        temperatureSensor2NotAssemble (210),
        extendTemperatureSensor1NotAssemble (211),
        extendTemperatureSensor2NotAssemble (212),
        bmm1CommunicationFault  (213),
        bmm2CommunicationFault  (214),
        bmm3CommunicationFault  (215),
        bmm4CommunicationFault  (216),
        bmm5CommunicationFault  (217),
        bmm6CommunicationFault  (218),
        bmm7CommunicationFault  (219),
        bmm8CommunicationFault  (220),
        bmm9CommunicationFault  (221),
        bmm10CommunicationFault (222),
        dg1Communicationfault   (223),
        dg2Communicationfault   (224),
        dg3Communicationfault   (225),
        extend2TemperatureSensor1NotAssemble    (226),
        extend2TemperatureSensor2NotAssemble    (227),
        extend3TemperatureSensor1NotAssemble    (228),
        extend3TemperatureSensor2NotAssemble    (229),
        extend4TemperatureSensor1NotAssemble    (230),
        extend4TemperatureSensor2NotAssemble    (231),
        extend5TemperatureSensor1NotAssemble    (232),
        extend5TemperatureSensor2NotAssemble    (233),
        sc350-1CommunicationFault (234),
        sc350-2CommunicationFault (235),
        sc350-3CommunicationFault (236),
        
        lLVD1 (252),
        lLVD2 (253),
        lLVD3 (254),
        lLVD4 (255),
        lLVD5 (256),
        lLVD6 (257),
        lLVD7 (258),
        lLVD8 (259),
        bLVD (260),
        lLVD1Fail (261),
        lLVD2Fail (262),
        lLVD3Fail (263),
        lLVD4Fail (264),
        lLVD5Fail (265),
        lLVD6Fail (266),
        lLVD7Fail (267),
        lLVD8Fail (268),
        bLVDFail (269),
        preAlarmlLVD1 (270),
        preAlarmlLVD2 (271),
        preAlarmlLVD3 (272),
        preAlarmlLVD4 (273),
        preAlarmlLVD5 (274),
        preAlarmlLVD6 (275),
        preAlarmlLVD7 (276),
        preAlarmlLVD8 (277),
        preAlarmbLVD (278),

        battery1Break (333),
        battery2Break (334),
        battery3Break (335),
        battery4Break (336),
        battery5Break (337),
        battery6Break (338),
        battery7Break (339),
        battery8Break (340),
        
        battery1NegtiveBreak (404),
        battery2NegtiveBreak (405),
        battery3NegtiveBreak (406),
        battery4NegtiveBreak (407),
        battery5NegtiveBreak (408),
        battery6NegtiveBreak (409),
        battery7NegtiveBreak (410),
        battery8NegtiveBreak (411),
        
        batteryChargeOverCurrent (475),
        batteryDischarge (476),
        batteryQuickTestOverCurrent (477),
        battery1MiddleImbalance (478),
        battery2MiddleImbalance (479),
        battery3MiddleImbalance (480),
        battery4MiddleImbalance (481),
        battery5MiddleImbalance (482),
        battery6MiddleImbalance (483),
        battery7MiddleImbalance (484),
        battery8MiddleImbalance (485),
        battery1CanNotCharge(486),
        battery2CanNotCharge(487),
        battery3CanNotCharge(488),
        battery4CanNotCharge(489),
        battery5CanNotCharge(490),
        battery6CanNotCharge(491),
        battery7CanNotCharge(492),
        battery8CanNotCharge(493),
        batteryTestFail(494),

        dcBranch1SlightOverCurrent (549),
        dcBranch2SlightOverCurrent (550),
        dcBranch3SlightOverCurrent (551),
        dcBranch4SlightOverCurrent (552),
        dcBranch5SlightOverCurrent (553),
        dcBranch6SlightOverCurrent (554),
        dcBranch7SlightOverCurrent (555),
        dcBranch8SlightOverCurrent (556),
        dcBranch9SlightOverCurrent (557),
        dcBranch10SlightOverCurrent (558),
        dcBranch11SlightOverCurrent (559),
        dcBranch12SlightOverCurrent (560),
        dcBranch13SlightOverCurrent (561),
        dcBranch14SlightOverCurrent (562),
        dcBranch15SlightOverCurrent (563),
        dcBranch16SlightOverCurrent (564),
        dcBranch17SlightOverCurrent (565),
        dcBranch18SlightOverCurrent (566),
        dcBranch19SlightOverCurrent (567),
        dcBranch20SlightOverCurrent (568),
        dcBranch21SlightOverCurrent (569),
        dcBranch22SlightOverCurrent (570),
        dcBranch23SlightOverCurrent (571),
        dcBranch24SlightOverCurrent (572),
        dcBranch25SlightOverCurrent (573),
        dcBranch26SlightOverCurrent (574),
        dcBranch27SlightOverCurrent (575),
        dcBranch28SlightOverCurrent (576),
        dcBranch29SlightOverCurrent (577),
        dcBranch30SlightOverCurrent (578),
        dcBranch31SlightOverCurrent (579),
        dcBranch32SlightOverCurrent (580),
        dcBranch33SlightOverCurrent (581),
        dcBranch34SlightOverCurrent (582),
        dcBranch35SlightOverCurrent (583),
        dcBranch36SlightOverCurrent (584),
        dcBranch37SlightOverCurrent (585),
        dcBranch38SlightOverCurrent (586),
        dcBranch39SlightOverCurrent (587),
        dcBranch40SlightOverCurrent (588),
        dcBranch41SlightOverCurrent (589),
        dcBranch42SlightOverCurrent (590),
        dcBranch43SlightOverCurrent (591),
        dcBranch44SlightOverCurrent (592),
        dcBranch45SlightOverCurrent (593),
        dcBranch46SlightOverCurrent (594),
        dcBranch47SlightOverCurrent (595),
        dcBranch48SlightOverCurrent (596),
        dcBranch49SlightOverCurrent (597),
        dcBranch50SlightOverCurrent (598),
        dcBranch51SlightOverCurrent (599),
        dcBranch52SlightOverCurrent (600),
        dcBranch53SlightOverCurrent (601),
        dcBranch54SlightOverCurrent (602),
        dcBranch55SlightOverCurrent (603),
        dcBranch56SlightOverCurrent (604),
        dcBranch57SlightOverCurrent (605),
        dcBranch58SlightOverCurrent (606),
        dcBranch59SlightOverCurrent (607),
        dcBranch60SlightOverCurrent (608),
        dcBranch61SlightOverCurrent (609),
        dcBranch62SlightOverCurrent (610),
        dcBranch63SlightOverCurrent (611),
        dcBranch64SlightOverCurrent (612),
        dcBranch65SlightOverCurrent (613),
        dcBranch66SlightOverCurrent (614),
        dcBranch67SlightOverCurrent (615),
        dcBranch68SlightOverCurrent (616),
        dcBranch69SlightOverCurrent (617),
        dcBranch70SlightOverCurrent (618),
        dcBranch71SlightOverCurrent (619),
        dcBranch72SlightOverCurrent (620),
        
        dcBranch1SevereOverCurrent (684),
        dcBranch2SevereOverCurrent (685),
        dcBranch3SevereOverCurrent (686),
        dcBranch4SevereOverCurrent (687),
        dcBranch5SevereOverCurrent (688),
        dcBranch6SevereOverCurrent (689),
        dcBranch7SevereOverCurrent (690),
        dcBranch8SevereOverCurrent (691),
        dcBranch9SevereOverCurrent (692),
        dcBranch10SevereOverCurrent (693),
        dcBranch11SevereOverCurrent (694),
        dcBranch12SevereOverCurrent (695),
        dcBranch13SevereOverCurrent (696),
        dcBranch14SevereOverCurrent (697),
        dcBranch15SevereOverCurrent (698),
        dcBranch16SevereOverCurrent (699),
        dcBranch17SevereOverCurrent (700),
        dcBranch18SevereOverCurrent (701),
        dcBranch19SevereOverCurrent (702),
        dcBranch20SevereOverCurrent (703),
        dcBranch21SevereOverCurrent (704),
        dcBranch22SevereOverCurrent (705),
        dcBranch23SevereOverCurrent (706),
        dcBranch24SevereOverCurrent (707),
        dcBranch25SevereOverCurrent (708),
        dcBranch26SevereOverCurrent (709),
        dcBranch27SevereOverCurrent (710),
        dcBranch28SevereOverCurrent (711),
        dcBranch29SevereOverCurrent (712),
        dcBranch30SevereOverCurrent (713),
        dcBranch31SevereOverCurrent (714),
        dcBranch32SevereOverCurrent (715),
        dcBranch33SevereOverCurrent (716),
        dcBranch34SevereOverCurrent (717),
        dcBranch35SevereOverCurrent (718),
        dcBranch36SevereOverCurrent (719),
        dcBranch37SevereOverCurrent (720),
        dcBranch38SevereOverCurrent (721),
        dcBranch39SevereOverCurrent (722),
        dcBranch40SevereOverCurrent (723),
        dcBranch41SevereOverCurrent (724),
        dcBranch42SevereOverCurrent (725),
        dcBranch43SevereOverCurrent (726),
        dcBranch44SevereOverCurrent (727),
        dcBranch45SevereOverCurrent (728),
        dcBranch46SevereOverCurrent (729),
        dcBranch47SevereOverCurrent (730),
        dcBranch48SevereOverCurrent (731),
        dcBranch49SevereOverCurrent (732),
        dcBranch50SevereOverCurrent (733),
        dcBranch51SevereOverCurrent (734),
        dcBranch52SevereOverCurrent (735),
        dcBranch53SevereOverCurrent (736),
        dcBranch54SevereOverCurrent (737),
        dcBranch55SevereOverCurrent (738),
        dcBranch56SevereOverCurrent (739),
        dcBranch57SevereOverCurrent (740),
        dcBranch58SevereOverCurrent (741),
        dcBranch59SevereOverCurrent (742),
        dcBranch60SevereOverCurrent (743),
        dcBranch61SevereOverCurrent (744),
        dcBranch62SevereOverCurrent (745),
        dcBranch63SevereOverCurrent (746),
        dcBranch64SevereOverCurrent (747),
        dcBranch65SevereOverCurrent (748),
        dcBranch66SevereOverCurrent (749),
        dcBranch67SevereOverCurrent (750),
        dcBranch68SevereOverCurrent (751),
        dcBranch69SevereOverCurrent (752),
        dcBranch70SevereOverCurrent (753),
        dcBranch71SevereOverCurrent (754),
        dcBranch72SevereOverCurrent (755),

        loadBreak (819),
        load1Break (820),
        load2Break (821),
        load3Break (822),
        load4Break (823),
        load5Break (824),
        load6Break (825),
        load7Break (826),
        load8Break (827),
        load9Break (828),
        load10Break (829),
        load11Break (830),
        load12Break (831),
        load13Break (832),
        load14Break (833),
        load15Break (834),
        load16Break (835),
        load17Break (836),
        load18Break (837),
        load19Break (838),
        load20Break (839),
        load21Break (840),
        load22Break (841),
        load23Break (842),
        load24Break (843),
        load25Break (844),
        load26Break (845),
        load27Break (846),
        load28Break (847),
        load29Break (848),
        load30Break (849),
        load31Break (850),
        load32Break (851),
        load33Break (852),
        load34Break (853),
        load35Break (854),
        load36Break (855),
        load37Break (856),
        load38Break (857),
        load39Break (858),
        load40Break (859),
        load41Break (860),
        load42Break (861),
        load43Break (862),
        load44Break (863),
        load45Break (864),
        load46Break (865),
        load47Break (866),
        load48Break (867),
        load49Break (868),
        load50Break (869),
        load51Break (870),
        load52Break (871),
        load53Break (872),
        load54Break (873),
        load55Break (874),
        load56Break (875),
        load57Break (876),
        load58Break (877),
        load59Break (878),
        load60Break (879),
        load61Break (880),
        load62Break (881),
        load63Break (882),
        load64Break (883),
        load65Break (884),
        load66Break (885),
        load67Break (886),
        load68Break (887),
        load69Break (888),
        load70Break (889),
        load71Break (890),
        load72Break (891),

        ambientTemperature1High1(1525),
        ambientTemperature2High1(1526),
        ambientTemperature3High1(1527),
        ambientTemperature4High1(1528),
        ambientTemperature5High1(1529),
        ambientTemperature6High1(1530),
        ambientTemperature7High1(1531),
        ambientTemperature8High1(1532),
        ambientTemperature1High2(1533),
        ambientTemperature2High2(1534),
        ambientTemperature3High2(1535),
        ambientTemperature4High2(1536),
        ambientTemperature5High2(1537),
        ambientTemperature6High2(1538),
        ambientTemperature7High2(1539),
        ambientTemperature8High2(1540),
        ambientTemperature1Low1(1541),
        ambientTemperature2Low1(1542),
        ambientTemperature3Low1(1543),
        ambientTemperature4Low1(1544),
        ambientTemperature5Low1(1545),
        ambientTemperature6Low1(1546),
        ambientTemperature7Low1(1547),
        ambientTemperature8Low1(1548),
        ambientTemperature1Low2(1549),
        ambientTemperature2Low2(1550),
        ambientTemperature3Low2(1551),
        ambientTemperature4Low2(1552),
        ambientTemperature5Low2(1553),
        ambientTemperature6Low2(1554),
        ambientTemperature7Low2(1555),
        ambientTemperature8Low2(1556),
        humidityHigh(1557),
        humidityLow(1558),
        
        batteryTemperature1High1(1620),
        batteryTemperature2High1(1621),
        batteryTemperature3High1(1622),
        batteryTemperature4High1(1623),
        batteryTemperature5High1(1624),
        batteryTemperature6High1(1625),
        batteryTemperature7High1(1626),
        batteryTemperature8High1(1627),
        batteryTemperature1High2(1628),
        batteryTemperature2High2(1629),
        batteryTemperature3High2(1630),
        batteryTemperature4High2(1631),
        batteryTemperature5High2(1632),
        batteryTemperature6High2(1633),
        batteryTemperature7High2(1634),
        batteryTemperature8High2(1635),
        batteryTemperature1Low1(1636),
        batteryTemperature2Low1(1637),
        batteryTemperature3Low1(1638),
        batteryTemperature4Low1(1639),
        batteryTemperature5Low1(1640),
        batteryTemperature6Low1(1641),
        batteryTemperature7Low1(1642),
        batteryTemperature8Low1(1643),
        batteryTemperature1Low2(1644),
        batteryTemperature2Low2(1645),
        batteryTemperature3Low2(1646),
        batteryTemperature4Low2(1647),
        batteryTemperature5Low2(1648),
        batteryTemperature6Low2(1649),
        batteryTemperature7Low2(1650),
        batteryTemperature8Low2(1651),
        bTRMHigh1(1652),
        bTRMHigh2(1653),

        digitalInput1Alarm(1715),
        digitalInput2Alarm(1716),
        digitalInput3Alarm(1717),
        digitalInput4Alarm(1718),
        digitalInput5Alarm(1719),
        digitalInput6Alarm(1720),
        extend1digitalInput1Alarm(1721),
        extend1digitalInput2Alarm(1722),
        extend1digitalInput3Alarm(1723),
        extend1digitalInput4Alarm(1724),
        extend1digitalInput5Alarm(1725),
        extend1digitalInput6Alarm(1726),
        extend1digitalInput7Alarm(1727),
        extend1digitalInput8Alarm(1728),
        extend2digitalInput1Alarm(1729),
        extend2digitalInput2Alarm(1730),
        extend2digitalInput3Alarm(1731),
        extend2digitalInput4Alarm(1732),
        extend2digitalInput5Alarm(1733),
        extend2digitalInput6Alarm(1734),
        extend2digitalInput7Alarm(1735),
        extend2digitalInput8Alarm(1736),
        extend3digitalInput1Alarm(1737),
        extend3digitalInput2Alarm(1738),
        extend3digitalInput3Alarm(1739),
        extend3digitalInput4Alarm(1740),
        extend3digitalInput5Alarm(1741),
        extend3digitalInput6Alarm(1742),
        extend3digitalInput7Alarm(1743),
        extend3digitalInput8Alarm(1744),
        extend4digitalInput1Alarm(1745),
        extend4digitalInput2Alarm(1746),
        extend4digitalInput3Alarm(1747),
        extend4digitalInput4Alarm(1748),
        extend4digitalInput5Alarm(1749),
        extend4digitalInput6Alarm(1750),
        extend4digitalInput7Alarm(1751),
        extend4digitalInput8Alarm(1752),
        extend5digitalInput1Alarm(1753),
        extend5digitalInput2Alarm(1754),
        extend5digitalInput3Alarm(1755),
        extend5digitalInput4Alarm(1756),
        extend5digitalInput5Alarm(1757),
        extend5digitalInput6Alarm(1758),
        extend5digitalInput7Alarm(1759),
        extend5digitalInput8Alarm(1760),
        
        rectifierCurrentSampleFault(2042),
        rectifierPrimarySideCircuitShort(2043),
        mutipleRectifierNoOutput(2044),
        singleRectifierNooutput(2045),
        rectifierOutsideCircuitShort(2046),
        rectifierPFCImbalance(2047),
        rectifierIdentifyFault(2048),
        rectifierLost(2049),
        rectifierCurrentSharingSlightlyFault(2050),
        rectifierCurrentSharingSevereFault(2051),
        rectifierNoPosition(2052),
        rectifierOutputOverCurrent(2053),
        rectifierE2PROMFault(2054),
        rectifierCANCommunicationFault(2055),
        rectifierSecondSideCommmunicationFault(2056),
        rectifierPrimarySideCommmunicationFault(2057),
        rectifierFanFault(2058),
        rectifierStartResistorBreak(2059),
        rectifierPFCOvervoltageProtection(2060),
        rectifierPFCUndervoltageProtection(2061),
        rectifierACImbalance(2062),
        rectifierACLosePhase(2063),
        rectifierACUnderVoltageProtection(2064),
        rectifierACOverVoltageProtection(2065),
        rectifierInternalCircuitShort(2066),
        rectifierOutputFuseBreak(2067),
        rectifierSecondaryHotPointOverTemperature(2068),
        rectifierPrimaryHotPointOverTemperature(2069),
        rectifierAmbientOverTemperature(2070),
        rectifierOutputUnderVoltageProtection(2071),
        rectifierOuterOverVoltageProtection(2072),
        rectifierInternalOverVoltageProtection(2073),
        rectifierPFCShort(2074),
        rectifierOVSD(2075),
        rectifierSecurityCodeError(2076),
        
        rectifierSingleFault(2090),
        rectifierMutipleFault(2091),
        
        bmsTotalAlarm(2502),
        bmsBatteryOverCurrent(2503),
        bmsBatteryPacksOverVoltage(2504),
        bmsBatteryPacksUnderVoltage(2505),
        bmsBatteryCellOverVoltage(2506),
        bmsBatteryCellUnderVoltage(2507),
        bmsBatteryHighTenmperature(2508),
        bmsBatteryLowTenmperature(2509),
        bmsBatteryOutputShort(2510),
        bmsBatteryLowSOC(2511),
        
        plcArithmetic1Alarm(2575),
        plcArithmetic2Alarm(2576),
        plcArithmetic3Alarm(2577),
        plcArithmetic4Alarm(2578),
        plcArithmetic5Alarm(2579),
        plcArithmetic6Alarm(2580),
        plcArithmetic7Alarm(2581),
        plcArithmetic8Alarm(2582),
        plcArithmetic9Alarm(2583),
        plcArithmetic10Alarm(2584),
        plcArithmetic11Alarm(2585),
        plcArithmetic12Alarm(2586),
        plcArithmetic13Alarm(2587),
        plcArithmetic14Alarm(2588),
        plcArithmetic15Alarm(2589),
        plcArithmetic16Alarm(2590),
        plcArithmetic17Alarm(2591),
        plcArithmetic18Alarm(2592),
        plcArithmetic19Alarm(2593),
        plcArithmetic20Alarm(2594),
        plcArithmetic21Alarm(2595),
        plcArithmetic22Alarm(2596),
        plcArithmetic23Alarm(2597),
        plcArithmetic24Alarm(2598),
        plcArithmetic25Alarm(2599),
        plcArithmetic26Alarm(2600),
        plcArithmetic27Alarm(2601),
        plcArithmetic28Alarm(2602),
        plcArithmetic29Alarm(2603),
        plcArithmetic30Alarm(2604),
        plcArithmetic31Alarm(2605),
        plcArithmetic32Alarm(2606),
        plcArithmetic33Alarm(2607),
        plcArithmetic34Alarm(2608),
        plcArithmetic35Alarm(2609),
        plcArithmetic36Alarm(2610),
        plcArithmetic37Alarm(2611),
        plcArithmetic38Alarm(2612),
        plcArithmetic39Alarm(2613),
        plcArithmetic40Alarm(2614),
        
        plcLogic1Alarm(2646),
        plcLogic2Alarm(2647),
        plcLogic3Alarm(2648),
        plcLogic4Alarm(2649),
        plcLogic5Alarm(2650),
        plcLogic6Alarm(2651),
        plcLogic7Alarm(2652),
        plcLogic8Alarm(2653),
        plcLogic9Alarm(2654),
        plcLogic10Alarm(2655),
        
        plcGroup1Alarm(2687),
        plcGroup2Alarm(2688),
        plcGroup3Alarm(2689),
        plcGroup4Alarm(2690),
        plcGroup5Alarm(2691),
        plcGroup6Alarm(2692),
        plcGroup7Alarm(2693),
        plcGroup8Alarm(2694),
        plcGroup9Alarm(2695),
        plcGroup10Alarm(2696),
        plcGroup11Alarm(2697),
        plcGroup12Alarm(2698),
        plcGroup13Alarm(2699),
        plcGroup14Alarm(2700),
        plcGroup15Alarm(2701),
        plcGroup16Alarm(2702),
        plcGroup17Alarm(2703),
        plcGroup18Alarm(2704),
        plcGroup19Alarm(2705),
        plcGroup20Alarm(2706),
        plcGroup21Alarm(2707),
        plcGroup22Alarm(2708),
        plcGroup23Alarm(2709),
        plcGroup24Alarm(2710),
        plcGroup25Alarm(2711),
        plcGroup26Alarm(2712),
        plcGroup27Alarm(2713),
        plcGroup28Alarm(2714),
        plcGroup29Alarm(2715),
        plcGroup30Alarm(2716),
        bmm-TotalAlarm(2780),
        bmm-BatteryOverCurrent(2781),
        bmm-BatteryPacksOverVoltage(2782),
        bmm-BatteryPacksUnderVoltage(2783),
        bmm-BatteryCellOverVoltage(2784),
        bmm-BatteryCellUnderVoltage(2785),
        bmm-BatteryHighTenmperature(2786),
        bmm-BatteryLowTenmperature(2787),
        bmm-BatteryHighResistance(2788),
        userAlarm1  (2853),
        userAlarm2  (2854),
        userAlarm3  (2855),
        userAlarm4  (2856),
        userAlarm5  (2857),
        userAlarm6  (2858),
        userAlarm7  (2859),
        userAlarm8  (2860),
        userAlarm9  (2861),
        userAlarm10 (2862),
        userAlarm11 (2863),
        userAlarm12 (2864),
        userAlarm13 (2865),
        userAlarm14 (2866),
        userAlarm15 (2867),
        userAlarm16 (2868),

        dgTotalAlarm    (2932),
        dgEmergencyStop (2933),
        dgStartFail (2934),
        dgStopFail  (2935),
        dgOilPressureLow    (2936),
        dgEngineTemperatureHigh (2937),
        dgOverSpeed (2938),
        dgUnderSpeed    (2939),
        dgOverLoad  (2940),
        dgFuelLevelLow  (2941),
        sc350_1Alarm    (3005),
        sc350_2Alarm    (3006),
        sc350_3Alarm    (3007)
        "
    ::= { activeAlarmEntry 1 }

alarmTime OBJECT-TYPE
    SYNTAX DisplayString
    MAX-ACCESS read-only
    STATUS current
    DESCRIPTION "
        Date and time when event occured (local time), including
        timezone if supported by controller."
    ::= { activeAlarmEntry 2 }

alarmLevel OBJECT-TYPE
    SYNTAX Integer32 {
        minor (0),
        major (1),
        critical (2)
    }
    MAX-ACCESS read-only
    STATUS current
    DESCRIPTION "
        The severity of the alarm. One of
        (0) minor - MI, lowest level of alarm severity
        (1) major - MA
        (2) critical - CA, highest level of alarm severity"
    ::= { activeAlarmEntry 3 }

alarmType OBJECT-TYPE
    SYNTAX Integer32 {
        notUsed (0),
        acAlarm (1),
        dcAlarm (2),
        communicationAlarm (3),
        lvdAlarm (4),
        batteryFuseAlarm (5),
        batteryNFuseAlarm (6),
        batteryAlarm (7),
        loadFuseAlarm (8),
        environmentTemperatureAlarm (9),
        batteryTemperatureAlarm (10),
        digitalInputAlarm (11),
        rectifierAlarm (12),
        solarControllerAlarm (13),
        windControllerAlarm (14),
        inverterAlarm (15),
        dcdcConverterAlarm (16),
        slightOverCurrentAlarm (17),
        severeOverCurrentAlarm (18),
        bmsAlarm (19),
        plcAirthmeticAlarm (20),
        plcLogicAlarm (21),
        plcGroupAlarm (22),
        bmmAlarm (23),
        userAlarm(24),
        dgAlarm(25),
        sc350Alarm(26)
    }
    MAX-ACCESS read-only
    STATUS current
    DESCRIPTION "
        Alarm type, i.e. an integer specifying the type of alarm.
        notUsed (0),
        acAlarm (1),
        dcAlarm (2),
        communicationAlarm (3),
        lvdAlarm (4),
        batteryFuseAlarm (5),
        batteryNFuseAlarm (6),
        batteryAlarm (7),
        loadFuseAlarm (8),
        environmentTemperatureAlarm (9),
        batteryTemperatureAlarm (10),
        digitalInputAlarm (11),
        rectifierAlarm (12),
        solarControllerAlarm (13),
        windControllerAlarm (14),
        inverterAlarm (15),
        dcdcConverterAlarm (16),
        slightOverCurrentAlarm (17),
        severeOverCurrentAlarm (18),
        bmsAlarm (19),
        plcAirthmeticAlarm (20),
        plcLogicAlarm (21),
        plcGroupAlarm (22),
        bmmAlarm (23),
        userAlarm(24),
        dgAlarm(25),
        sc350Alarm(26)"
    ::= { activeAlarmEntry 4 }
    
alarmRelateDOPosition OBJECT-TYPE
    SYNTAX Integer32 {
        notUsed (0),
        controller (1),
        extendDOBorad1 (2),
        extendDOBorad2 (3),
        extendDOBorad3 (4),
        extendDOBorad4 (5),
        extendDOBorad5 (6)
    }
    MAX-ACCESS read-only
    STATUS current
    DESCRIPTION "
        The position of the relay-out for the alarm.
        notUsed (0),
        controller (1),
        extendDOBorad1 (2),
        extendDOBorad2 (3),
        extendDOBorad3 (4),
        extendDOBorad4 (5),
        extendDOBorad5 (6)"
    ::= { activeAlarmEntry 5 }
    
alarmRelateDO OBJECT-TYPE
    SYNTAX Integer32 {
        relayOut1 (0),
        relayOut2 (1),
        relayOut3 (2),
        relayOut4 (3),
        relayOut5 (4),
        relayOut6 (5),
        relayOut7 (6),
        relayOut8 (7),
        relayOut9 (8),
        relayOut10 (9),
        relayOut11 (10),
        relayOut12 (11),
        relayOut13 (12),
        relayOut14 (13),
        relayOut15 (14),
        relayOut16 (15)
    }
    MAX-ACCESS read-only
    STATUS current
    DESCRIPTION "
        The relay-out number for the alarm.
        relayOut1 (0),
        relayOut2 (1),
        relayOut3 (2),
        relayOut4 (3),
        relayOut5 (4),
        relayOut6 (5),
        relayOut7 (6),
        relayOut8 (7),
        relayOut9 (8),
        relayOut10 (9),
        relayOut11 (10),
        relayOut12 (11),
        relayOut13 (12),
        relayOut14 (13),
        relayOut15 (14),
        relayOut16 (15)"
    ::= { activeAlarmEntry 6 }
    
alarmBuzzer OBJECT-TYPE
    SYNTAX Integer32 {
        silent (0),
        sound (1)
    }
    MAX-ACCESS read-only
    STATUS current
    DESCRIPTION "
        The alarm configuration for the buzzer.One of
        (0) silent - no sound for alarm
        (1) sound - sound for alarm"
    ::= { activeAlarmEntry 7 }
    
alarmMoudleID OBJECT-TYPE
    SYNTAX Integer32 {
        notMoudleAlarm (0)
    }
    MAX-ACCESS read-only
    STATUS current
    DESCRIPTION "
        The moudle ID number of the moudle.This is only for 
        rectifierAlarm, solarControllerAlarm, windControllerAlarm, 
        inverterAlarm, dcdcConverterAlarm.
        (0) not the moudle alarm
        (1..128) the moudle ID number of the moudle"
    ::= { activeAlarmEntry 8 }

alarmStatusChange OBJECT-TYPE
    SYNTAX Integer32{
        deactivated (0),
        activated (1)
    }
    MAX-ACCESS read-only
    STATUS current
    DESCRIPTION "
        The status of alarm. One of
        (0) deactivated
        (1) activated"
    ::= { activeAlarmEntry 9 }
alarmName OBJECT-TYPE
    SYNTAX DisplayString
    MAX-ACCESS read-only
    STATUS current
    DESCRIPTION 
        "Alarm name."
    ::= { activeAlarmEntry 10 }
------------------------------------------------------------
-- Events/traps { systemAlarm 3 }
------------------------------------------------------------

systemTraps OBJECT IDENTIFIER ::= { systemAlarm 3 }

alarmTrap NOTIFICATION-TYPE
    OBJECTS {
        alarmIndex,
        alarmTime,
        alarmLevel,
        alarmType,
        alarmRelateDOPosition,
        alarmRelateDO,
        alarmBuzzer,
        alarmMoudleID,
        alarmStatusChange
    }
    STATUS current
    DESCRIPTION "
        An alarm trap is sent when an alarm occurs (activated) or
        returns to normal state (deactivated). Alarm traps are logged
        in alarmTrapTable. Variables in this trap:
        * alarmIndex - The unique sequence number of this alarm trap.
        * alarmTime - Date and time when event occured (local time),
              including timezone if supported by controller.
        * alarmLevel - Integer describing the severity of the alarm.
        * alarmType - Integer indicating type of alarm.
        * alarmRelateDOPosition - The position of the relay-out for the alarm.
        * alarmRelateDO - The relay-out number for the alarm.
        * alarmBuzzer - The alarm configuration for the buzzer.
        * alarmMoudleID - The moudle ID number of the moudle.
        * alarmStatusChange - The status of alarm."
    ::= { systemTraps 1 }


alarmActiveTrap NOTIFICATION-TYPE
    OBJECTS {
        alarmIndex,
        alarmTime,
        alarmLevel,
        alarmType,
        alarmRelateDOPosition,
        alarmRelateDO,
        alarmBuzzer,
        alarmMoudleID
    }
    STATUS current
    DESCRIPTION "
        An alarm trap is sent when an alarm occurs (activated).
        Alarm traps are logged in alarmTrapTable. Variables in this trap:
        * alarmIndex - The unique sequence number of this alarm trap.
        * alarmTime - Date and time when event occured (local time),
              including timezone if supported by controller.
        * alarmLevel - Integer describing the severity of the alarm.
        * alarmType - Integer indicating type of alarm.
        * alarmRelateDOPosition - The position of the relay-out for the alarm.
        * alarmRelateDO - The relay-out number for the alarm.
        * alarmBuzzer - The alarm configuration for the buzzer.
        * alarmMoudleID - The moudle ID number of the moudle."
    ::= { systemTraps 2 }
    
alarmCeaseTrap NOTIFICATION-TYPE
    OBJECTS {
        alarmIndex,
        alarmTime,
        alarmLevel,
        alarmType,
        alarmRelateDOPosition,
        alarmRelateDO,
        alarmBuzzer,
        alarmMoudleID
    }
    STATUS current
    DESCRIPTION "
        An alarm trap is sent when an alarm returns to normal state (clear, deactivated). 
        Alarm traps are logged in alarmTrapTable. Variables in this trap:
        * alarmIndex - The unique sequence number of this alarm trap.
        * alarmTime - Date and time when event occured (local time),
              including timezone if supported by controller.
        * alarmLevel - Integer describing the severity of the alarm.
        * alarmType - Integer indicating type of alarm.
        * alarmRelateDOPosition - The position of the relay-out for the alarm.
        * alarmRelateDO - The relay-out number for the alarm.
        * alarmBuzzer - The alarm configuration for the buzzer.
        * alarmMoudleID - The moudle ID number of the moudle."
    ::= { systemTraps 3 }  
    
------------------------------------------------------------
-- End of MIB definitions
------------------------------------------------------------

END
